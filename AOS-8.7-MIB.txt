XIRRUS-MIB      DEFINITIONS ::= BEGIN

IMPORTS
    MODULE-IDENTITY, OBJECT-TYPE, NOTIFICATION-TYPE, enterprises,
    IpAddress, Counter32, Counter64 FROM SNMPv2-SMI

    DisplayString, MacAddress, RowStatus FROM SNMPv2-TC;

    xirrus      MODULE-IDENTITY
        LAST-UPDATED    "201605231200Z"
        ORGANIZATION    "Xirrus"
        CONTACT-INFO    "support@xirrus.com"
        DESCRIPTION     "Xirrus enterprise MIB tree"
        REVISION        "201605231200Z"
        DESCRIPTION     "xirrus mib"
        ::=  { enterprises 21013 }


    products            OBJECT IDENTIFIER ::= { xirrus 1 }


    xmManage            OBJECT IDENTIFIER ::= { products 1   }
    xsArray             OBJECT IDENTIFIER ::= { products 2   }
    xs3500Array         OBJECT IDENTIFIER ::= { products 100 }
    xs3700Array         OBJECT IDENTIFIER ::= { products 101 }
    xs3900Array         OBJECT IDENTIFIER ::= { products 102 }
    xs3500-512Array     OBJECT IDENTIFIER ::= { products 103 }
    xs3700-1GArray      OBJECT IDENTIFIER ::= { products 104 }
    xs3900-1GArray      OBJECT IDENTIFIER ::= { products 105 }
    xs4Array            OBJECT IDENTIFIER ::= { products 106 }
    xs8Array            OBJECT IDENTIFIER ::= { products 107 }
    xs16Array           OBJECT IDENTIFIER ::= { products 108 }
    xn4Array            OBJECT IDENTIFIER ::= { products 109 }
    xn8Array            OBJECT IDENTIFIER ::= { products 110 }
    xn16Array           OBJECT IDENTIFIER ::= { products 111 }
    xs12Array           OBJECT IDENTIFIER ::= { products 112 }
    xn12Array           OBJECT IDENTIFIER ::= { products 113 }
    xr4420Array         OBJECT IDENTIFIER ::= { products 114 }
    xr4430Array         OBJECT IDENTIFIER ::= { products 115 }
    xr4820Array         OBJECT IDENTIFIER ::= { products 116 }
    xr4830Array         OBJECT IDENTIFIER ::= { products 117 }
    xr6820Array         OBJECT IDENTIFIER ::= { products 118 }
    xr6830Array         OBJECT IDENTIFIER ::= { products 119 }
    xr7220Array         OBJECT IDENTIFIER ::= { products 120 }
    xr7230Array         OBJECT IDENTIFIER ::= { products 121 }
    xr7620Array         OBJECT IDENTIFIER ::= { products 122 }
    xr7630Array         OBJECT IDENTIFIER ::= { products 123 }
    xr1220Array         OBJECT IDENTIFIER ::= { products 124 }
    xr1230Array         OBJECT IDENTIFIER ::= { products 125 }
    xr2420Array         OBJECT IDENTIFIER ::= { products 126 }
    xr2430Array         OBJECT IDENTIFIER ::= { products 127 }
    xr2220Array         OBJECT IDENTIFIER ::= { products 128 }
    xr2230Array         OBJECT IDENTIFIER ::= { products 129 }
    xr1120Array         OBJECT IDENTIFIER ::= { products 130 }
    xr1130Array         OBJECT IDENTIFIER ::= { products 131 }
    xr1120hArray        OBJECT IDENTIFIER ::= { products 132 }
    xr1130hArray        OBJECT IDENTIFIER ::= { products 133 }
    xr520hArray         OBJECT IDENTIFIER ::= { products 134 }
    xr1230hArray        OBJECT IDENTIFIER ::= { products 135 }
    xr2420hArray        OBJECT IDENTIFIER ::= { products 136 }
    xr2430hArray        OBJECT IDENTIFIER ::= { products 137 }
    xr2220hArray        OBJECT IDENTIFIER ::= { products 138 }
    xr2230hArray        OBJECT IDENTIFIER ::= { products 139 }
    xr520Array          OBJECT IDENTIFIER ::= { products 142 }
    xr530Array          OBJECT IDENTIFIER ::= { products 143 }
    xr1220hArray        OBJECT IDENTIFIER ::= { products 144 }
    xr530hArray         OBJECT IDENTIFIER ::= { products 145 }
    xr420hArray         OBJECT IDENTIFIER ::= { products 146 }
    xr430hArray         OBJECT IDENTIFIER ::= { products 147 }
    xr2425Array         OBJECT IDENTIFIER ::= { products 148 }
    xr2435Array         OBJECT IDENTIFIER ::= { products 149 }
    xr2425hArray        OBJECT IDENTIFIER ::= { products 150 }
    xr2225Array         OBJECT IDENTIFIER ::= { products 151 }
    xr2235Array         OBJECT IDENTIFIER ::= { products 152 }
    xr620Array          OBJECT IDENTIFIER ::= { products 153 }
    xr620hArray         OBJECT IDENTIFIER ::= { products 154 }
    xr630Array          OBJECT IDENTIFIER ::= { products 155 }
    xr2426Array         OBJECT IDENTIFIER ::= { products 156 }
    xr2436Array         OBJECT IDENTIFIER ::= { products 157 }
    xr2426hArray        OBJECT IDENTIFIER ::= { products 158 }
    xr2226Array         OBJECT IDENTIFIER ::= { products 159 }
    xr2226hArray        OBJECT IDENTIFIER ::= { products 160 }
    xr2236Array         OBJECT IDENTIFIER ::= { products 161 }
    xr630hArray         OBJECT IDENTIFIER ::= { products 162 }
    xr2225hArray        OBJECT IDENTIFIER ::= { products 163 }
    xr2235hArray        OBJECT IDENTIFIER ::= { products 164 }
    xr2236hArray        OBJECT IDENTIFIER ::= { products 165 }
    xr2435hArray        OBJECT IDENTIFIER ::= { products 166 }
    xr2436hArray        OBJECT IDENTIFIER ::= { products 167 }
    xr1126Array         OBJECT IDENTIFIER ::= { products 168 }
    xr1136Array         OBJECT IDENTIFIER ::= { products 169 }
    xr1226Array         OBJECT IDENTIFIER ::= { products 170 }
    xr1236Array         OBJECT IDENTIFIER ::= { products 171 }
    xr1126hArray        OBJECT IDENTIFIER ::= { products 172 }
    xr1136hArray        OBJECT IDENTIFIER ::= { products 173 }
    xr1226hArray        OBJECT IDENTIFIER ::= { products 174 }
    xr1236hArray        OBJECT IDENTIFIER ::= { products 175 }
    xr4426Array         OBJECT IDENTIFIER ::= { products 176 }
    xr4436Array         OBJECT IDENTIFIER ::= { products 177 }
    xr4826Array         OBJECT IDENTIFIER ::= { products 178 }
    xr4836Array         OBJECT IDENTIFIER ::= { products 179 }
    xr6826Array         OBJECT IDENTIFIER ::= { products 180 }
    xr6836Array         OBJECT IDENTIFIER ::= { products 181 }
    xr7226Array         OBJECT IDENTIFIER ::= { products 182 }
    xr7236Array         OBJECT IDENTIFIER ::= { products 183 }
    xr7626Array         OBJECT IDENTIFIER ::= { products 184 }
    xr7636Array         OBJECT IDENTIFIER ::= { products 185 }
    xd1-130Array        OBJECT IDENTIFIER ::= { products 186 }
    xd2-130Array        OBJECT IDENTIFIER ::= { products 187 }
    xd4-130Array        OBJECT IDENTIFIER ::= { products 188 }
    xd8-130Array        OBJECT IDENTIFIER ::= { products 189 }
    xh1-130Array        OBJECT IDENTIFIER ::= { products 190 }
    xh2-130Array        OBJECT IDENTIFIER ::= { products 191 }
    xh4-130Array        OBJECT IDENTIFIER ::= { products 192 }
    xh8-130Array        OBJECT IDENTIFIER ::= { products 193 }
    xd1-240Array        OBJECT IDENTIFIER ::= { products 194 }
    xd2-240Array        OBJECT IDENTIFIER ::= { products 195 }
    xd4-240Array        OBJECT IDENTIFIER ::= { products 196 }
    xd8-240Array        OBJECT IDENTIFIER ::= { products 197 }
    xh1-240Array        OBJECT IDENTIFIER ::= { products 198 }
    xh2-240Array        OBJECT IDENTIFIER ::= { products 199 }
    xh4-240Array        OBJECT IDENTIFIER ::= { products 200 }
    xh8-240Array        OBJECT IDENTIFIER ::= { products 201 }
    xd1-120Array        OBJECT IDENTIFIER ::= { products 202 }
    xd2-120Array        OBJECT IDENTIFIER ::= { products 203 }
    xd4-120Array        OBJECT IDENTIFIER ::= { products 204 }
    xd8-120Array        OBJECT IDENTIFIER ::= { products 205 }
    xh1-120Array        OBJECT IDENTIFIER ::= { products 206 }
    xh2-120Array        OBJECT IDENTIFIER ::= { products 207 }
    xh4-120Array        OBJECT IDENTIFIER ::= { products 208 }
    xh8-120Array        OBJECT IDENTIFIER ::= { products 209 }
    xr1147Array         OBJECT IDENTIFIER ::= { products 210 }
    xr1247Array         OBJECT IDENTIFIER ::= { products 211 }
    xr2247Array         OBJECT IDENTIFIER ::= { products 212 }
    xr2447Array         OBJECT IDENTIFIER ::= { products 213 }
    xr1147hArray        OBJECT IDENTIFIER ::= { products 214 }
    xr1247hArray        OBJECT IDENTIFIER ::= { products 215 }
    xr2247hArray        OBJECT IDENTIFIER ::= { products 216 }
    xr2447hArray        OBJECT IDENTIFIER ::= { products 217 }
    xr4447Array         OBJECT IDENTIFIER ::= { products 218 }
    xr4847Array         OBJECT IDENTIFIER ::= { products 219 }
    xr6847Array         OBJECT IDENTIFIER ::= { products 220 }
    xr7247Array         OBJECT IDENTIFIER ::= { products 221 }
    xr7647Array         OBJECT IDENTIFIER ::= { products 222 }
    xa1-120Array        OBJECT IDENTIFIER ::= { products 223 }
    xa2-120Array        OBJECT IDENTIFIER ::= { products 224 }
    xa4-120Array        OBJECT IDENTIFIER ::= { products 225 }
    xa8-120Array        OBJECT IDENTIFIER ::= { products 226 }
    xa1-130Array        OBJECT IDENTIFIER ::= { products 227 }
    xa2-130Array        OBJECT IDENTIFIER ::= { products 228 }
    xa4-130Array        OBJECT IDENTIFIER ::= { products 229 }
    xa8-130Array        OBJECT IDENTIFIER ::= { products 230 }
    xa1-240Array        OBJECT IDENTIFIER ::= { products 231 }
    xa2-240Array        OBJECT IDENTIFIER ::= { products 232 }
    xa4-240Array        OBJECT IDENTIFIER ::= { products 233 }
    xa8-240Array        OBJECT IDENTIFIER ::= { products 234 }
    xd1-230Array        OBJECT IDENTIFIER ::= { products 235 }
    xd2-230Array        OBJECT IDENTIFIER ::= { products 236 }
    xd3-230Array        OBJECT IDENTIFIER ::= { products 237 }
    xd4-230Array        OBJECT IDENTIFIER ::= { products 238 }
    xd8-230Array        OBJECT IDENTIFIER ::= { products 239 }
    xh1-230Array        OBJECT IDENTIFIER ::= { products 240 }
    xh2-230Array        OBJECT IDENTIFIER ::= { products 241 }
    xh3-230Array        OBJECT IDENTIFIER ::= { products 242 }
    xh4-230Array        OBJECT IDENTIFIER ::= { products 243 }
    xh8-230Array        OBJECT IDENTIFIER ::= { products 244 }
    xa1-230Array        OBJECT IDENTIFIER ::= { products 245 }
    xa2-230Array        OBJECT IDENTIFIER ::= { products 246 }
    xa3-230Array        OBJECT IDENTIFIER ::= { products 247 }
    xa4-230Array        OBJECT IDENTIFIER ::= { products 248 }
    xa8-230Array        OBJECT IDENTIFIER ::= { products 249 }
    xa3-240Array        OBJECT IDENTIFIER ::= { products 250 }
    xh3-240Array        OBJECT IDENTIFIER ::= { products 251 }
    xd3-240Array        OBJECT IDENTIFIER ::= { products 252 }

-- xsArray

    acl         OBJECT IDENTIFIER ::= { xsArray 2 }
    admin       OBJECT IDENTIFIER ::= { xsArray 4 }
    cdp         OBJECT IDENTIFIER ::= { xsArray 5 }
    dateTime    OBJECT IDENTIFIER ::= { xsArray 6 }
    dhcp        OBJECT IDENTIFIER ::= { xsArray 8 }
    dns         OBJECT IDENTIFIER ::= { xsArray 10 }
    filter      OBJECT IDENTIFIER ::= { xsArray 11 }
    interface   OBJECT IDENTIFIER ::= { xsArray 12 }
    networkMap  OBJECT IDENTIFIER ::= { xsArray 13 }
    radius      OBJECT IDENTIFIER ::= { xsArray 14 }
    roamAssist  OBJECT IDENTIFIER ::= { xsArray 15 }
    security    OBJECT IDENTIFIER ::= { xsArray 16 }
    snmpAgent   OBJECT IDENTIFIER ::= { xsArray 18 }
    ssid        OBJECT IDENTIFIER ::= { xsArray 20 }
    stations    OBJECT IDENTIFIER ::= { xsArray 22 }
    statistics  OBJECT IDENTIFIER ::= { xsArray 24 }
    syslog      OBJECT IDENTIFIER ::= { xsArray 26 }
    system      OBJECT IDENTIFIER ::= { xsArray 28 }
    tunnel      OBJECT IDENTIFIER ::= { xsArray 29 }
    vlan        OBJECT IDENTIFIER ::= { xsArray 30 }
    cluster     OBJECT IDENTIFIER ::= { xsArray 31 }
    envCtrl     OBJECT IDENTIFIER ::= { xsArray 32 }
    location    OBJECT IDENTIFIER ::= { xsArray 33 }
    group       OBJECT IDENTIFIER ::= { xsArray 34 }
    mdm         OBJECT IDENTIFIER ::= { xsArray 35 }
    netflow     OBJECT IDENTIFIER ::= { xsArray 36 }
    wifiTag     OBJECT IDENTIFIER ::= { xsArray 37 }
    wpr         OBJECT IDENTIFIER ::= { xsArray 38 }
    oauth       OBJECT IDENTIFIER ::= { xsArray 39 }
    proxyFwd    OBJECT IDENTIFIER ::= { xsArray 40 }
    proxyMgmt   OBJECT IDENTIFIER ::= { xsArray 41 }
    lldp        OBJECT IDENTIFIER ::= { xsArray 42 }
    position    OBJECT IDENTIFIER ::= { xsArray 43 }
    traps       OBJECT IDENTIFIER ::= { xsArray 50 }


--
-- ACL
--

    aclEnable OBJECT-TYPE
        SYNTAX          INTEGER { disable(0), allow(1) , deny(2), deny-include-blocked-rogues(3) }
        MAX-ACCESS      read-write
        STATUS          current
        DESCRIPTION
            "Access Control List enable"
        ::= { acl 1 }

    aclTable OBJECT-TYPE
        SYNTAX          SEQUENCE OF AclEntry
        MAX-ACCESS      not-accessible
        STATUS          current
        DESCRIPTION
            "Access Control List for the Array"
        ::= { acl 2 }

    aclEntry OBJECT-TYPE
        SYNTAX          AclEntry
        MAX-ACCESS      not-accessible
        STATUS          current
        DESCRIPTION
            "ACL table entry"
        INDEX       { aclIndex }
        ::= { aclTable 1 }

    AclEntry ::= SEQUENCE {
        aclIndex        Integer32,
        aclMacAddress   DisplayString,
        aclRowStatus    RowStatus
    }

    aclIndex OBJECT-TYPE
        SYNTAX          Integer32
        MAX-ACCESS      not-accessible
        STATUS          current
        DESCRIPTION
            "Access Control List Index"
        ::= { aclEntry 1 }

    aclMacAddress OBJECT-TYPE
        SYNTAX          DisplayString(SIZE(1..17))
        MAX-ACCESS      read-create
        STATUS          current
        DESCRIPTION
            "Mac address to be allowed or denied"
        ::= { aclEntry 2 }

    aclRowStatus OBJECT-TYPE
        SYNTAX          RowStatus
        MAX-ACCESS      read-create
        STATUS          current
        DESCRIPTION
            "Status of the ACL row entry"
        ::= { aclEntry 3 }

    aclTableReset OBJECT-TYPE
        SYNTAX          INTEGER { reset(1) }
        MAX-ACCESS      read-write
        STATUS          current
        DESCRIPTION
            "Reset Access Control List (clear all entries)"
        ::= { acl 3 }

    aclSsidTable OBJECT-TYPE
        SYNTAX          SEQUENCE OF AclSsidEntry
        MAX-ACCESS      not-accessible
        STATUS          current
        DESCRIPTION
            "Access Control List per SSID"
        ::= { acl 4 }

    aclSsidEntry OBJECT-TYPE
        SYNTAX          AclSsidEntry
        MAX-ACCESS      not-accessible
        STATUS          current
        DESCRIPTION
            "ACL per SSID table entry"
        INDEX       { aclSsidIndex }
        ::= { aclSsidTable 1 }

    AclSsidEntry ::= SEQUENCE {
        aclSsidIndex        Integer32,
        aclSsidMacAddress   DisplayString,
        aclSsidName         DisplayString,
        aclSsidRowStatus    RowStatus
    }

    aclSsidIndex OBJECT-TYPE
        SYNTAX          Integer32
        MAX-ACCESS      not-accessible
        STATUS          current
        DESCRIPTION
            "ACL per SSID index"
        ::= { aclSsidEntry 1 }

    aclSsidMacAddress OBJECT-TYPE
        SYNTAX          DisplayString(SIZE(1..17))
        MAX-ACCESS      read-create
        STATUS          current
        DESCRIPTION
            "Mac address to be allowed or denied"
        ::= { aclSsidEntry 2 }

    aclSsidName OBJECT-TYPE
        SYNTAX          DisplayString(SIZE(1..32))
        MAX-ACCESS      read-create
        STATUS          current
        DESCRIPTION
            "SSID this ACL entry belongs to"
        ::= { aclSsidEntry 3 }

    aclSsidRowStatus OBJECT-TYPE
        SYNTAX          RowStatus
        MAX-ACCESS      read-create
        STATUS          current
        DESCRIPTION
            "Status of the ACL row entry"
        ::= { aclSsidEntry 4 }

    aclSsidTableReset OBJECT-TYPE
        SYNTAX          DisplayString(SIZE(1..32))
        MAX-ACCESS      read-write
        STATUS          current
        DESCRIPTION
            "Reset ACL (clear all entries) for given SSID"
        ::= { acl 5 }

--
-- ADMIN
--

    adminTable OBJECT-TYPE
        SYNTAX          SEQUENCE OF AdminEntry
        MAX-ACCESS      not-accessible
        STATUS          current
        DESCRIPTION
            "Administrator List for the Array"
        ::= { admin 1 }

    adminEntry OBJECT-TYPE
        SYNTAX          AdminEntry
        MAX-ACCESS      not-accessible
        STATUS          current
        DESCRIPTION
            "Admin table entry"
        INDEX       { adminIndex }
        ::= { adminTable 1 }

    AdminEntry ::= SEQUENCE {
        adminIndex          Integer32,
        adminUsername       DisplayString,
        adminPassword       DisplayString,
        adminPasswordForm   INTEGER,
        adminPrivilege      INTEGER,
        adminRowStatus      RowStatus,
        adminPrivilegeLevel Integer32
    }

    adminIndex OBJECT-TYPE
        SYNTAX          Integer32
        MAX-ACCESS      not-accessible
        STATUS          current
        DESCRIPTION
            "Admin Index"
        ::= { adminEntry 1 }

    adminUsername OBJECT-TYPE
        SYNTAX          DisplayString(SIZE(5..50))
        MAX-ACCESS      read-create
        STATUS          current
        DESCRIPTION
            "Admin username"
        ::= { adminEntry 2 }

    adminPassword OBJECT-TYPE
        SYNTAX          DisplayString(SIZE(5..50))
        MAX-ACCESS      read-create
        STATUS          current
        DESCRIPTION
            "Admin password"
        ::= { adminEntry 3 }

    adminPasswordForm OBJECT-TYPE
        SYNTAX          INTEGER { clear(0), encrypted(1) }
        MAX-ACCESS      read-create
        STATUS          current
        DESCRIPTION
            "Admin password form"
        ::= { adminEntry 4 }

    adminPrivilege OBJECT-TYPE
        SYNTAX          INTEGER { read-only(0), read-write(1) }
        MAX-ACCESS      read-create
        STATUS          current
        DESCRIPTION
            "Admin privilege"
        ::= { adminEntry 5 }

    adminRowStatus OBJECT-TYPE
        SYNTAX          RowStatus
        MAX-ACCESS      read-create
        STATUS          current
        DESCRIPTION
            "Status of the admin row entry"
        ::= { adminEntry 6 }

    adminPrivilegeLevel OBJECT-TYPE
        SYNTAX          Integer32(0..7)
        MAX-ACCESS      read-create
        STATUS          current
        DESCRIPTION
            "Admin privilege level"
        ::= { adminEntry 7 }

    adminTableReset OBJECT-TYPE
        SYNTAX          INTEGER { reset(1) }
        MAX-ACCESS      read-write
        STATUS          current
        DESCRIPTION
            "Reset administrator list (clear all entries and restore default)"
        ::= { admin 2 }

    adminTableClear OBJECT-TYPE
        SYNTAX          INTEGER { clear(1) }
        MAX-ACCESS      read-write
        STATUS          current
        DESCRIPTION
            "Clear all entries in administrator list"
        ::= { admin 3 }

    adminRadius         OBJECT IDENTIFIER ::= { admin 4 }

--
-- ADMIN RADIUS
--

    adminRadiusEnable OBJECT-TYPE
        SYNTAX          INTEGER { disable(0), enable(1) }
        MAX-ACCESS      read-write
        STATUS          current
        DESCRIPTION
            "Enable or disable admin authentication via Radius"
        ::= { adminRadius 1 }

    adminRadiusPriServer OBJECT-TYPE
        SYNTAX          DisplayString(SIZE(0.. 255))
        MAX-ACCESS      read-write
        STATUS          current
        DESCRIPTION
            "Admin Primary Radius server host name or IP address"
        ::= { adminRadius 2 }

    adminRadiusPriServerPort OBJECT-TYPE
        SYNTAX          Integer32(0..65535)
        MAX-ACCESS      read-write
        STATUS          current
        DESCRIPTION
            "Admin Primary Radius server port"
        ::= { adminRadius 3 }

    adminRadiusPriServerSecret OBJECT-TYPE
        SYNTAX          DisplayString(SIZE(0..64))
        MAX-ACCESS      read-write
        STATUS          current
        DESCRIPTION
            "Admin Primary Radius server secret"
        ::= { adminRadius 4 }

    adminRadiusPriServerSecretEnc OBJECT-TYPE
        SYNTAX          DisplayString(SIZE(0..128))
        MAX-ACCESS      read-write
        STATUS          current
        DESCRIPTION
            "Admin Primary Radius server secret (encrypted)"
        ::= { adminRadius 5 }

    adminRadiusSecServer OBJECT-TYPE
        SYNTAX          DisplayString(SIZE(0.. 255))
        MAX-ACCESS      read-write
        STATUS          current
        DESCRIPTION
            "Admin Secondary Radius server host name or IP address"
        ::= { adminRadius 6 }

    adminRadiusSecServerPort OBJECT-TYPE
        SYNTAX          Integer32(0..65535)
        MAX-ACCESS      read-write
        STATUS          current
        DESCRIPTION
            "Admin Secondary Radius server port"
        ::= { adminRadius 7 }

    adminRadiusSecServerSecret OBJECT-TYPE
        SYNTAX          DisplayString(SIZE(0..64))
        MAX-ACCESS      read-write
        STATUS          current
        DESCRIPTION
            "Admin Secondary Radius server secret"
        ::= { adminRadius 8 }

    adminRadiusSecServerSecretEnc OBJECT-TYPE
        SYNTAX          DisplayString(SIZE(0..128))
        MAX-ACCESS      read-write
        STATUS          current
        DESCRIPTION
            "Admin Secondary Radius server secret (encrypted)"
        ::= { adminRadius 9 }

    adminRadiusTimeout OBJECT-TYPE
        SYNTAX          Integer32(0..65535)
        MAX-ACCESS      read-write
        STATUS          current
        DESCRIPTION
            "Timeout before server is retried after it initially failed"
        ::= { adminRadius 10 }

    adminRadiusAuthType OBJECT-TYPE
        SYNTAX          INTEGER { chap(0), pap(1), ms-chap(2) }
        MAX-ACCESS      read-write
        STATUS          current
        DESCRIPTION
            "Set authentication protocol for admin authentication via RADIUS"
        ::= { adminRadius 11 }

    adminHistoryTable OBJECT-TYPE
        SYNTAX          SEQUENCE OF AdminHistoryEntry
        MAX-ACCESS      not-accessible
        STATUS          current
        DESCRIPTION
            "Administrator history list"
        ::= { admin 5 }

    adminHistoryEntry OBJECT-TYPE
        SYNTAX          AdminHistoryEntry
        MAX-ACCESS      not-accessible
        STATUS          current
        DESCRIPTION
            "Administrator history table entry"
        INDEX       {  adminHistoryIndex }
        ::= {  adminHistoryTable 1 }

    AdminHistoryEntry ::= SEQUENCE {
        adminHistoryIndex           Integer32,
        adminHistoryUsername        DisplayString,
        adminHistoryIPAddress       DisplayString,
        adminHistoryInterface       INTEGER,
        adminHistoryLoginTime       DisplayString,
        adminHistoryLogoutTime      DisplayString
    }

    adminHistoryIndex OBJECT-TYPE
        SYNTAX          Integer32
        MAX-ACCESS      not-accessible
        STATUS          current
        DESCRIPTION
            "Admin history table index"
        ::= { adminHistoryEntry 1 }

    adminHistoryUsername OBJECT-TYPE
        SYNTAX          DisplayString
        MAX-ACCESS      read-only
        STATUS          current
        DESCRIPTION
            "Admin username"
        ::= { adminHistoryEntry 2 }

    adminHistoryIPAddress OBJECT-TYPE
        SYNTAX          DisplayString
        MAX-ACCESS      read-only
        STATUS          current
        DESCRIPTION
            "IP Address admin logged in from"
        ::= { adminHistoryEntry 3 }

    adminHistoryInterface OBJECT-TYPE
        SYNTAX          INTEGER { console(0), telnet(1), ssh(2), https(3) }
        MAX-ACCESS      read-only
        STATUS          current
        DESCRIPTION
            "Interface admin logged in via"
        ::= { adminHistoryEntry 4 }

    adminHistoryLoginTime OBJECT-TYPE
        SYNTAX          DisplayString
        MAX-ACCESS      read-only
        STATUS          current
        DESCRIPTION
            "Admin login time"
        ::= { adminHistoryEntry 5 }

    adminHistoryLogoutTime OBJECT-TYPE
        SYNTAX          DisplayString
        MAX-ACCESS      read-only
        STATUS          current
        DESCRIPTION
            "Admin logout time"
        ::= { adminHistoryEntry 6 }

    adminPrivLevelTable OBJECT-TYPE
        SYNTAX          SEQUENCE OF AdminPrivLevelEntry
        MAX-ACCESS      not-accessible
        STATUS          current
        DESCRIPTION
            "Administrator privilege level table"
        ::= { admin 6 }

    adminPrivLevelEntry OBJECT-TYPE
        SYNTAX          AdminPrivLevelEntry
        MAX-ACCESS      not-accessible
        STATUS          current
        DESCRIPTION
            "Administrator privilege level table entry"
        INDEX       { adminPrivLevelNumber }
        ::= { adminPrivLevelTable 1 }

    AdminPrivLevelEntry ::= SEQUENCE {
        adminPrivLevelNumber        Integer32,
        adminPrivLevelName          DisplayString
    }

    adminPrivLevelNumber OBJECT-TYPE
        SYNTAX          Integer32
        MAX-ACCESS      read-only
        STATUS          current
        DESCRIPTION
            "Administrator privilege level number"
        ::= { adminPrivLevelEntry 1 }

    adminPrivLevelName OBJECT-TYPE
        SYNTAX          DisplayString(SIZE(1..20))
        MAX-ACCESS      read-write
        STATUS          current
        DESCRIPTION
            "Administrator privilege level name"
        ::= { adminPrivLevelEntry 2 }

    adminPrivSectionTable OBJECT-TYPE
        SYNTAX          SEQUENCE OF AdminPrivSectionEntry
        MAX-ACCESS      not-accessible
        STATUS          current
        DESCRIPTION
            "Administrator privilege section table"
        ::= { admin 7 }

    adminPrivSectionEntry OBJECT-TYPE
        SYNTAX          AdminPrivSectionEntry
        MAX-ACCESS      not-accessible
        STATUS          current
        DESCRIPTION
            "Administrator privilege section table entry"
        INDEX       { adminPrivSectionIndex }
        ::= { adminPrivSectionTable 1 }

    AdminPrivSectionEntry ::= SEQUENCE {
        adminPrivSectionIndex       Integer32,
        adminPrivSectionName        DisplayString,
        adminPrivSectionLevel       Integer32
    }

    adminPrivSectionIndex OBJECT-TYPE
        SYNTAX          Integer32
        MAX-ACCESS      not-accessible
        STATUS          current
        DESCRIPTION
            "Administrator privilege section table index"
        ::= { adminPrivSectionEntry 1 }

    adminPrivSectionName OBJECT-TYPE
        SYNTAX          DisplayString
        MAX-ACCESS      read-only
        STATUS          current
        DESCRIPTION
            "Administrator privilege section name"
        ::= { adminPrivSectionEntry 2 }

    adminPrivSectionLevel OBJECT-TYPE
        SYNTAX          Integer32(0..7)
        MAX-ACCESS      read-write
        STATUS          current
        DESCRIPTION
            "Administrator privilege level required by config section"
        ::= { adminPrivSectionEntry 3 }

--
-- CDP
--

    cdpInfoTable OBJECT-TYPE
        SYNTAX          SEQUENCE OF CdpInfoEntry
        MAX-ACCESS      not-accessible
        STATUS          current
        DESCRIPTION
            "Cisco Discovery Protocol information table"
        ::= { cdp 1 }

    cdpInfoEntry OBJECT-TYPE
        SYNTAX          CdpInfoEntry
        MAX-ACCESS      not-accessible
        STATUS          current
        DESCRIPTION
            "CDP info table entry"
        INDEX       { cdpInfoIndex }
        ::= { cdpInfoTable 1 }

    CdpInfoEntry ::= SEQUENCE {
        cdpInfoIndex            Integer32,
        cdpInfoHostname         DisplayString,
        cdpInfoIPAddress        DisplayString,
        cdpInfoModel            DisplayString,
        cdpInfoInterface        DisplayString,
        cdpInfoNativeVlan       DisplayString,
        cdpInfoCapabilities     DisplayString,
        cdpInfoSoftware         DisplayString
    }

    cdpInfoIndex OBJECT-TYPE
        SYNTAX          Integer32
        MAX-ACCESS      not-accessible
        STATUS          current
        DESCRIPTION
            "CDP info table index"
        ::= { cdpInfoEntry 1 }

    cdpInfoHostname OBJECT-TYPE
        SYNTAX          DisplayString
        MAX-ACCESS      read-only
        STATUS          current
        DESCRIPTION
            "Device hostname"
        ::= { cdpInfoEntry 2 }

    cdpInfoIPAddress OBJECT-TYPE
        SYNTAX          DisplayString
        MAX-ACCESS      read-only
        STATUS          current
        DESCRIPTION
            "Device IP Address"
        ::= { cdpInfoEntry 3 }

    cdpInfoModel OBJECT-TYPE
        SYNTAX          DisplayString
        MAX-ACCESS      read-only
        STATUS          current
        DESCRIPTION
            "Device model"
        ::= { cdpInfoEntry 4 }

    cdpInfoInterface OBJECT-TYPE
        SYNTAX          DisplayString
        MAX-ACCESS      read-only
        STATUS          current
        DESCRIPTION
            "Device interface"
        ::= { cdpInfoEntry 5 }

    cdpInfoNativeVlan OBJECT-TYPE
        SYNTAX          DisplayString
        MAX-ACCESS      read-only
        STATUS          current
        DESCRIPTION
            "Device native vlan"
        ::= { cdpInfoEntry 6 }

    cdpInfoCapabilities OBJECT-TYPE
        SYNTAX          DisplayString
        MAX-ACCESS      read-only
        STATUS          current
        DESCRIPTION
            "Device capabilities"
        ::= { cdpInfoEntry 7 }

    cdpInfoSoftware OBJECT-TYPE
        SYNTAX          DisplayString
        MAX-ACCESS      read-only
        STATUS          current
        DESCRIPTION
            "Device software"
        ::= { cdpInfoEntry 8 }

    cdpEnable OBJECT-TYPE
        SYNTAX          INTEGER { disable(0), enable(1) }
        MAX-ACCESS      read-write
        STATUS          current
        DESCRIPTION
            "Enable or disable CDP"
        ::= { cdp 2 }

    cdpInterval OBJECT-TYPE
        SYNTAX          Integer32(5..900)
        MAX-ACCESS      read-write
        STATUS          current
        DESCRIPTION
            "CDP message interval (in seconds)"
        ::= { cdp 3 }

    cdpHoldTime OBJECT-TYPE
        SYNTAX          Integer32(10..255)
        MAX-ACCESS      read-write
        STATUS          current
        DESCRIPTION
            "CDP message hold time (in seconds)"
        ::= { cdp 4 }

--
-- DATE/TIME
--

    dateTimeSet OBJECT-TYPE
        SYNTAX          DisplayString(SIZE(1..12))
        MAX-ACCESS      read-write
        STATUS          current
        DESCRIPTION
            "Date and time. To set use the following format: MMDDhhmmYYYY"
        ::= { dateTime 1 }

    dateTimeZoneHours OBJECT-TYPE
        SYNTAX          Integer32(-12..12)
        MAX-ACCESS      read-write
        STATUS          current
        DESCRIPTION
            "Hours offset from UTC"
        ::= { dateTime 2 }

    dateTimeZoneMins OBJECT-TYPE
        SYNTAX          Integer32(0..59)
        MAX-ACCESS      read-write
        STATUS          current
        DESCRIPTION
            "Minutes offset from UTC"
        ::= { dateTime 3 }

    dateTimeDSTAdjust OBJECT-TYPE
        SYNTAX          INTEGER { disable(0), enable(1) }
        MAX-ACCESS      read-write
        STATUS          current
        DESCRIPTION
            "Enable or disable DST adjustment"
        ::= { dateTime 4 }

    ntp     OBJECT IDENTIFIER ::= { dateTime 5 }

--
-- DATE/TIME NTP
--

    ntpEnable OBJECT-TYPE
        SYNTAX          INTEGER { disable(0), enable(1) }
        MAX-ACCESS      read-write
        STATUS          current
        DESCRIPTION
            "Enable or disable NTP"
        ::= { ntp 1 }

    ntpPrimary OBJECT-TYPE
        SYNTAX          DisplayString(SIZE(1..255))
        MAX-ACCESS      read-write
        STATUS          current
        DESCRIPTION
            "Primary NTP IP address"
        ::= { ntp 2 }

    ntpSecondary OBJECT-TYPE
        SYNTAX          DisplayString(SIZE(1..255))
        MAX-ACCESS      read-write
        STATUS          current
        DESCRIPTION
            "Secondary NTP IP address"
        ::= { ntp 3 }

    ntpPrimaryAuthType OBJECT-TYPE
        SYNTAX          INTEGER { none(0), md5(1), sha1(2) }
        MAX-ACCESS      read-write
        STATUS          current
        DESCRIPTION
            "Primary NTP server authentication type"
        ::= { ntp 4 }

    ntpPrimaryAuthKeyID OBJECT-TYPE
        SYNTAX          Integer32(1..65534)
        MAX-ACCESS      read-write
        STATUS          current
        DESCRIPTION
            "Primary NTP server authentication key ID"
        ::= { ntp 5 }

    ntpPrimaryAuthKey OBJECT-TYPE
        SYNTAX          DisplayString(SIZE(0..20))
        MAX-ACCESS      read-write
        STATUS          current
        DESCRIPTION
            "Primary NTP server authentication key"
        ::= { ntp 6 }

    ntpPrimaryAuthKeyEnc OBJECT-TYPE
        SYNTAX          DisplayString(SIZE(0..40))
        MAX-ACCESS      read-write
        STATUS          current
        DESCRIPTION
            "Primary NTP server authentication key (encrypted)"
        ::= { ntp 7 }

    ntpSecondaryAuthType OBJECT-TYPE
        SYNTAX          INTEGER { none(0), md5(1), sha1(2) }
        MAX-ACCESS      read-write
        STATUS          current
        DESCRIPTION
            "Secondary NTP server authentication type"
        ::= { ntp 8 }

    ntpSecondaryAuthKeyID OBJECT-TYPE
        SYNTAX          Integer32(1..65534)
        MAX-ACCESS      read-write
        STATUS          current
        DESCRIPTION
            "Secondary NTP server authentication key ID"
        ::= { ntp 9 }

    ntpSecondaryAuthKey OBJECT-TYPE
        SYNTAX          DisplayString(SIZE(0..20))
        MAX-ACCESS      read-write
        STATUS          current
        DESCRIPTION
            "Secondary NTP server authentication key"
        ::= { ntp 10 }

    ntpSecondaryAuthKeyEnc OBJECT-TYPE
        SYNTAX          DisplayString(SIZE(0..40))
        MAX-ACCESS      read-write
        STATUS          current
        DESCRIPTION
            "Secondary NTP server authentication key (encrypted)"
        ::= { ntp 11 }

--
-- DHCP
--

    dhcpPoolTableReset OBJECT-TYPE
        SYNTAX          INTEGER { reset(1) }
        MAX-ACCESS      read-write
        STATUS          current
        DESCRIPTION
            "Reset DHCP table (clear all entries)"
        ::= { dhcp 1 }

    dhcpPoolTable OBJECT-TYPE
        SYNTAX          SEQUENCE OF DhcpPoolEntry
        MAX-ACCESS      not-accessible
        STATUS          current
        DESCRIPTION
            "DHCP pool table for the Array"
        ::= { dhcp 2 }

    dhcpPoolEntry OBJECT-TYPE
        SYNTAX          DhcpPoolEntry
        MAX-ACCESS      not-accessible
        STATUS          current
        DESCRIPTION
            "DHCP pool table entry"
        INDEX       { dhcpPoolIndex }
        ::= { dhcpPoolTable 1 }

    DhcpPoolEntry ::= SEQUENCE {
        dhcpPoolIndex               Integer32,
        dhcpPoolName                DisplayString,
        dhcpPoolEnable              INTEGER,
        dhcpPoolRangeStartIP        IpAddress,
        dhcpPoolRangeEndIP          IpAddress,
        dhcpPoolDefaultLease        Integer32,
        dhcpPoolMaxLease            Integer32,
        dhcpPoolMask                IpAddress,
        dhcpPoolGateway             IpAddress,
        dhcpPoolDNSDomain           DisplayString,
        dhcpPoolDNSServer1          IpAddress,
        dhcpPoolDNSServer2          IpAddress,
        dhcpPoolDNSServer3          IpAddress,
        dhcpPoolNAT                 INTEGER,
        dhcpPoolRowStatus           RowStatus
    }

    dhcpPoolIndex OBJECT-TYPE
        SYNTAX          Integer32
        MAX-ACCESS      not-accessible
        STATUS          current
        DESCRIPTION
            "DHCP pool table index"
        ::= { dhcpPoolEntry 1 }

    dhcpPoolName OBJECT-TYPE
        SYNTAX          DisplayString(SIZE(1..20))
        MAX-ACCESS      read-create
        STATUS          current
        DESCRIPTION
            "DHCP pool name"
        ::= { dhcpPoolEntry 2 }

    dhcpPoolEnable OBJECT-TYPE
        SYNTAX          INTEGER { disable(0), enable(1) }
        MAX-ACCESS      read-create
        STATUS          current
        DESCRIPTION
            "Enable or disable DHCP pool"
        ::= { dhcpPoolEntry 3 }

    dhcpPoolRangeStartIP OBJECT-TYPE
        SYNTAX          IpAddress
        MAX-ACCESS      read-create
        STATUS          current
        DESCRIPTION
            "DHCP pool address range start"
        ::= { dhcpPoolEntry 4 }

    dhcpPoolRangeEndIP OBJECT-TYPE
        SYNTAX          IpAddress
        MAX-ACCESS      read-create
        STATUS          current
        DESCRIPTION
            "DHCP pool address range end"
        ::= { dhcpPoolEntry 5 }

    dhcpPoolDefaultLease OBJECT-TYPE
        SYNTAX          Integer32(60..3000000)
        MAX-ACCESS      read-create
        STATUS          current
        DESCRIPTION
            "DHCP pool default lease (in seconds)"
        ::= { dhcpPoolEntry 6 }

    dhcpPoolMaxLease OBJECT-TYPE
        SYNTAX          Integer32(60..3000000)
        MAX-ACCESS      read-create
        STATUS          current
        DESCRIPTION
            "DHCP pool max lease (in seconds)"
        ::= { dhcpPoolEntry 7 }

    dhcpPoolMask OBJECT-TYPE
        SYNTAX          IpAddress
        MAX-ACCESS      read-create
        STATUS          current
        DESCRIPTION
            "DHCP pool subnet mask"
        ::= { dhcpPoolEntry 8 }

    dhcpPoolGateway OBJECT-TYPE
        SYNTAX          IpAddress
        MAX-ACCESS      read-create
        STATUS          current
        DESCRIPTION
            "DHCP pool gateway"
        ::= { dhcpPoolEntry 9 }

    dhcpPoolDNSDomain OBJECT-TYPE
        SYNTAX          DisplayString(SIZE(0..255))
        MAX-ACCESS      read-create
        STATUS          current
        DESCRIPTION
            "DHCP pool DNS domain"
        ::= { dhcpPoolEntry 10 }

    dhcpPoolDNSServer1 OBJECT-TYPE
        SYNTAX          IpAddress
        MAX-ACCESS      read-create
        STATUS          current
        DESCRIPTION
            "DHCP pool DNS first server"
        ::= { dhcpPoolEntry 11 }

    dhcpPoolDNSServer2 OBJECT-TYPE
        SYNTAX          IpAddress
        MAX-ACCESS      read-create
        STATUS          current
        DESCRIPTION
            "DHCP pool DNS second server"
        ::= { dhcpPoolEntry 12 }

    dhcpPoolDNSServer3 OBJECT-TYPE
        SYNTAX          IpAddress
        MAX-ACCESS      read-create
        STATUS          current
        DESCRIPTION
            "DHCP pool DNS third server"
        ::= { dhcpPoolEntry 13 }

    dhcpPoolNAT OBJECT-TYPE
        SYNTAX          INTEGER { disable(0), enable(1) }
        MAX-ACCESS      read-create
        STATUS          current
        DESCRIPTION
            "Enable or disable NAT"
        ::= { dhcpPoolEntry 14 }

    dhcpPoolRowStatus OBJECT-TYPE
        SYNTAX          RowStatus
        MAX-ACCESS      read-create
        STATUS          current
        DESCRIPTION
            "Status of the DHCP pool row entry"
        ::= { dhcpPoolEntry 15 }

--
-- DNS
--

    dnsDomain OBJECT-TYPE
        SYNTAX          DisplayString(SIZE(0..255))
        MAX-ACCESS      read-write
        STATUS          current
        DESCRIPTION
            "DNS Domain"
        ::= { dns 1 }

    dnsSrv1 OBJECT-TYPE
        SYNTAX          IpAddress
        MAX-ACCESS      read-write
        STATUS          current
        DESCRIPTION
            "DNS first server"
        ::= { dns 2 }

    dnsSrv2 OBJECT-TYPE
        SYNTAX          IpAddress
        MAX-ACCESS      read-write
        STATUS          current
        DESCRIPTION
            "DNS second server"
        ::= { dns 3 }

    dnsSrv3 OBJECT-TYPE
        SYNTAX          IpAddress
        MAX-ACCESS      read-write
        STATUS          current
        DESCRIPTION
            "DNS third server"
        ::= { dns 4 }

    dnsUseDhcp OBJECT-TYPE
        SYNTAX          INTEGER { disable(0), enable(1) }
        MAX-ACCESS      read-write
        STATUS          current
        DESCRIPTION
            "Enable or disable updates to DNS settings via DHCP"
        ::= { dns 5 }

--
-- FILTER
--

    filterMoveDown OBJECT-TYPE
        SYNTAX          DisplayString(SIZE(1..20))
        MAX-ACCESS      read-write
        STATUS          current
        DESCRIPTION
            "Decrease filter priority (Global filter list)"
        ::= { filter 1 }

    filterMoveUp OBJECT-TYPE
        SYNTAX          DisplayString(SIZE(1..20))
        MAX-ACCESS      read-write
        STATUS          current
        DESCRIPTION
            "Increase filter priority (Global filter list)"
        ::= { filter 2 }

    filterTableReset OBJECT-TYPE
        SYNTAX          INTEGER { reset(1) }
        MAX-ACCESS      read-write
        STATUS          current
        DESCRIPTION
            "Reset filter table and filter list table (clear all entries)"
        ::= { filter 3 }

    filterTable OBJECT-TYPE
        SYNTAX          SEQUENCE OF FilterEntry
        MAX-ACCESS      not-accessible
        STATUS          current
        DESCRIPTION
            "Filter table for the Array"
        ::= { filter 4 }

    filterEntry OBJECT-TYPE
        SYNTAX          FilterEntry
        MAX-ACCESS      not-accessible
        STATUS          current
        DESCRIPTION
            "Filter table entry"
        INDEX       { filterIndex }
        ::= { filterTable 1 }

    FilterEntry ::= SEQUENCE {
        filterIndex                 Integer32,
        filterName                  DisplayString,
        filterEnable                INTEGER,
        filterType                  INTEGER,
        filterProtocol              Integer32,
        filterPort                  Integer32,
        filterSrcType               INTEGER,
        filterSrcInvertSense        INTEGER,
        filterSrcSsid               DisplayString,
        filterSrcVlan               Integer32,
        filterSrcIPAddress          IpAddress,
        filterSrcIPAddressMask      IpAddress,
        filterSrcMacAddress         DisplayString,
        filterSrcMacAddressMask     DisplayString,
        filterSrcIface              INTEGER,
        filterDstType               INTEGER,
        filterDstInvertSense        INTEGER,
        filterDstSsid               DisplayString,
        filterDstVlan               Integer32,
        filterDstIPAddress          IpAddress,
        filterDstIPAddressMask      IpAddress,
        filterDstMacAddress         DisplayString,
        filterDstMacAddressMask     DisplayString,
        filterDstIface              INTEGER,
        filterSetQOS                Integer32,
        filterSetVlan               Integer32,
        filterPriority              Integer32,
        filterRowStatus             RowStatus,
        filterList                  DisplayString,
        filterPortRange             Integer32,
        filterSrcGroup              DisplayString,
        filterDstGroup              DisplayString,
        filterLog                   INTEGER,
        filterPackets               Counter64,
        filterBytes                 Counter64,
        filterApplication           DisplayString,
        filterLayer                 INTEGER,
        filterSetDSCP               Integer32,
        filterTrafficLimit          Integer32,
        filterTrafficLimitType      INTEGER,
        filterTimeOn                Integer32,
        filterTimeOff               Integer32,
        filterDays                  DisplayString,
	    filterSetIP		            DisplayString	

    }

    filterIndex OBJECT-TYPE
        SYNTAX          Integer32
        MAX-ACCESS      not-accessible
        STATUS          current
        DESCRIPTION
            "Filter table index"
        ::= { filterEntry 1 }

    filterName OBJECT-TYPE
        SYNTAX          DisplayString(SIZE(1..20))
        MAX-ACCESS      read-create
        STATUS          current
        DESCRIPTION
            "Filter name"
        ::= { filterEntry 2 }

    filterEnable OBJECT-TYPE
        SYNTAX          INTEGER { disable(0), enable(1) }
        MAX-ACCESS      read-create
        STATUS          current
        DESCRIPTION
            "Enable/disable filter"
        ::= { filterEntry 3 }

    filterType OBJECT-TYPE
        SYNTAX          INTEGER { allow(1), deny(2) }
        MAX-ACCESS      read-create
        STATUS          current
        DESCRIPTION
            "Filter type: allow/deny traffic"
        ::= { filterEntry 4 }

    filterProtocol OBJECT-TYPE
        SYNTAX          Integer32(0..255)
        MAX-ACCESS      read-create
        STATUS          current
        DESCRIPTION
            "Protocol to filter on (0 - any protocol, 255 - any IP protocol)"
        ::= { filterEntry 5 }

    filterPort OBJECT-TYPE
        SYNTAX          Integer32(0..65535)
        MAX-ACCESS      read-create
        STATUS          current
        DESCRIPTION
            "Port to filter on (0 - any port)"
        ::= { filterEntry 6 }

    filterSrcType OBJECT-TYPE
        SYNTAX          INTEGER { any(0), ssid(1), vlan(2), ip(3),
                                  mac(4), interface(5), group(6) }
        MAX-ACCESS      read-create
        STATUS          current
        DESCRIPTION
            "Filter source type"
        ::= { filterEntry 7 }

    filterSrcInvertSense OBJECT-TYPE
        SYNTAX          INTEGER { no(0), yes(1) }
        MAX-ACCESS      read-create
        STATUS          current
        DESCRIPTION
            "Invert sense of filter source address"
        ::= { filterEntry 8 }

    filterSrcSsid OBJECT-TYPE
        SYNTAX          DisplayString(SIZE(1..32))
        MAX-ACCESS      read-create
        STATUS          current
        DESCRIPTION
            "Filter source SSID"
        ::= { filterEntry 9 }

    filterSrcVlan OBJECT-TYPE
        SYNTAX          Integer32(0..4095)
        MAX-ACCESS      read-create
        STATUS          current
        DESCRIPTION
            "Filter source VLAN"
        ::= { filterEntry 10 }

    filterSrcIPAddress OBJECT-TYPE
        SYNTAX          IpAddress
        MAX-ACCESS      read-create
        STATUS          current
        DESCRIPTION
            "Filter source IP address"
        ::= { filterEntry 11 }

    filterSrcIPAddressMask OBJECT-TYPE
        SYNTAX          IpAddress
        MAX-ACCESS      read-create
        STATUS          current
        DESCRIPTION
            "Filter source IP address mask"
        ::= { filterEntry 12 }

    filterSrcMacAddress OBJECT-TYPE
        SYNTAX          DisplayString(SIZE(12..17))
        MAX-ACCESS      read-create
        STATUS          current
        DESCRIPTION
            "Filter source MAC address"
        ::= { filterEntry 13 }

    filterSrcMacAddressMask OBJECT-TYPE
        SYNTAX          DisplayString(SIZE(12..17))
        MAX-ACCESS      read-create
        STATUS          current
        DESCRIPTION
            "Filter source MAC address mask"
        ::= { filterEntry 14 }

    filterSrcIface OBJECT-TYPE
        SYNTAX          INTEGER { iap(0), wds-client-1(1), wds-client-2(2),
                                  wds-client-3(3), wds-client-4(4), wds-all(5),
                                  gig(6), wds-host-1(7), wds-host-2(8),
                                  wds-host-3(9), wds-host-4(10), tunnel(11) }
        MAX-ACCESS      read-create
        STATUS          current
        DESCRIPTION
            "Filter source interface"
        ::= { filterEntry 15 }

    filterDstType OBJECT-TYPE
        SYNTAX          INTEGER { any(0), ssid(1), vlan(2), ip(3),
                                  mac(4), interface(5), group(6) }
        MAX-ACCESS      read-create
        STATUS          current
        DESCRIPTION
            "Filter destination type"
        ::= { filterEntry 16 }

    filterDstInvertSense OBJECT-TYPE
        SYNTAX          INTEGER { no(0), yes(1) }
        MAX-ACCESS      read-create
        STATUS          current
        DESCRIPTION
            "Invert sense of filter destination address"
        ::= { filterEntry 17 }

    filterDstSsid OBJECT-TYPE
        SYNTAX          DisplayString(SIZE(1..32))
        MAX-ACCESS      read-create
        STATUS          current
        DESCRIPTION
            "Filter destination SSID"
        ::= { filterEntry 18 }

    filterDstVlan OBJECT-TYPE
        SYNTAX          Integer32(0..4095)
        MAX-ACCESS      read-create
        STATUS          current
        DESCRIPTION
            "Filter destination VLAN"
        ::= { filterEntry 19 }

    filterDstIPAddress OBJECT-TYPE
        SYNTAX          IpAddress
        MAX-ACCESS      read-create
        STATUS          current
        DESCRIPTION
            "Filter destination IP address"
        ::= { filterEntry 20 }

    filterDstIPAddressMask OBJECT-TYPE
        SYNTAX          IpAddress
        MAX-ACCESS      read-create
        STATUS          current
        DESCRIPTION
            "Filter destination IP address mask"
        ::= { filterEntry 21 }

    filterDstMacAddress OBJECT-TYPE
        SYNTAX          DisplayString(SIZE(12..17))
        MAX-ACCESS      read-create
        STATUS          current
        DESCRIPTION
            "Filter destination MAC address"
        ::= { filterEntry 22 }

    filterDstMacAddressMask OBJECT-TYPE
        SYNTAX          DisplayString(SIZE(12..17))
        MAX-ACCESS      read-create
        STATUS          current
        DESCRIPTION
            "Filter destination MAC address mask"
        ::= { filterEntry 23 }

    filterDstIface OBJECT-TYPE
        SYNTAX          INTEGER { iap(0), wds-client-1(1), wds-client-2(2),
                                  wds-client-3(3), wds-client-4(4), wds-all(5),
                                  gig(6), wds-host-1(7), wds-host-2(8),
                                  wds-host-3(9), wds-host-4(10), tunnel(11) }
        MAX-ACCESS      read-create
        STATUS          current
        DESCRIPTION
            "Filter destination interface"
        ::= { filterEntry 24 }

    filterSetQOS OBJECT-TYPE
        SYNTAX          Integer32(-1..3)
        MAX-ACCESS      read-create
        STATUS          current
        DESCRIPTION
            "Modify QoS setting for this filter (0..3), if -1 - do not modify QoS setting"
        ::= { filterEntry 25 }

    filterSetVlan OBJECT-TYPE
        SYNTAX          Integer32(-1..4095)
        MAX-ACCESS      read-create
        STATUS          current
        DESCRIPTION
            "Modify VLAN setting for this filter (0..4095), if -1 - do not modify VLAN setting"
        ::= { filterEntry 26 }

    filterPriority OBJECT-TYPE
        SYNTAX          Integer32(1..50)
        MAX-ACCESS      read-create
        STATUS          current
        DESCRIPTION
            "Filter priority"
        ::= { filterEntry 27 }

    filterRowStatus OBJECT-TYPE
        SYNTAX          RowStatus
        MAX-ACCESS      read-create
        STATUS          current
        DESCRIPTION
            "Status of the filter row entry"
        ::= { filterEntry 28 }

    filterList OBJECT-TYPE
        SYNTAX          DisplayString(SIZE(1..20))
        MAX-ACCESS      read-create
        STATUS          current
        DESCRIPTION
            "Filter list this filter belongs to"
        ::= { filterEntry 29 }

    filterPortRange OBJECT-TYPE
        SYNTAX          Integer32(0..65535)
        MAX-ACCESS      read-create
        STATUS          current
        DESCRIPTION
            "Port range ending number (0 - no range)"
        ::= { filterEntry 30 }

    filterSrcGroup OBJECT-TYPE
        SYNTAX          DisplayString(SIZE(1..32))
        MAX-ACCESS      read-create
        STATUS          current
        DESCRIPTION
            "Filter source user group"
        ::= { filterEntry 31 }

    filterDstGroup OBJECT-TYPE
        SYNTAX          DisplayString(SIZE(1..32))
        MAX-ACCESS      read-create
        STATUS          current
        DESCRIPTION
            "Filter destination user group"
        ::= { filterEntry 32 }

    filterLog OBJECT-TYPE
        SYNTAX          INTEGER { disable(0), enable(1) }
        MAX-ACCESS      read-create
        STATUS          current
        DESCRIPTION
            "Enable/disable filter packet logging"
        ::= { filterEntry 33 }

    filterPackets OBJECT-TYPE
        SYNTAX          Counter64
        MAX-ACCESS      read-only
        STATUS          current
        DESCRIPTION
            "The number of packets that matched the filter"
        ::= { filterEntry 34 }

    filterBytes OBJECT-TYPE
        SYNTAX          Counter64
        MAX-ACCESS      read-only
        STATUS          current
        DESCRIPTION
            "The number of bytes that matched the filter"
        ::= { filterEntry 35 }

    filterApplication OBJECT-TYPE
        SYNTAX          DisplayString(SIZE(0..8))
        MAX-ACCESS      read-create
        STATUS          current
        DESCRIPTION
            "Application GUID to filter on"
        ::= { filterEntry 36 }

    filterLayer OBJECT-TYPE
        SYNTAX          INTEGER { layer-2(0), layer-3(1) }
        MAX-ACCESS      read-create
        STATUS          current
        DESCRIPTION
            "Filter layer"
        ::= { filterEntry 37 }

    filterSetDSCP OBJECT-TYPE
        SYNTAX          Integer32(-1..63)
        MAX-ACCESS      read-create
        STATUS          current
        DESCRIPTION
            "Modify QoS setting for this filter (0..63), if -1 - do not modify DSCP setting"
        ::= { filterEntry 38 }

    filterTrafficLimit OBJECT-TYPE
        SYNTAX          Integer32(10..4000000)
        MAX-ACCESS      read-create
        STATUS          current
        DESCRIPTION
            "Filter traffic limit (10 to 1000000 if pps, 10 to 4000000 if Kbps)"
        ::= { filterEntry 39 }

    filterTrafficLimitType OBJECT-TYPE
        SYNTAX          INTEGER { none(0), all-pps(1), all-kbps(2), sta-pps(3), sta-kbps(4) }
        MAX-ACCESS      read-create
        STATUS          current
        DESCRIPTION
            "Filter traffic limit type"
        ::= { filterEntry 40 }

    filterTimeOn OBJECT-TYPE
        SYNTAX          Integer32(-1..1439)
        MAX-ACCESS      read-create
        STATUS          current
        DESCRIPTION
            "Time on for this filter in minutes after midnight"
        ::= { filterEntry 41 }

    filterTimeOff OBJECT-TYPE
        SYNTAX          Integer32(-1..1439)
        MAX-ACCESS      read-create
        STATUS          current
        DESCRIPTION
            "Time off for this filter in minutes after midnight"
        ::= { filterEntry 42 }

    filterDays OBJECT-TYPE
        SYNTAX          DisplayString(SIZE(0..100))
        MAX-ACCESS      read-create
        STATUS          current
        DESCRIPTION
            "Days of the week the filter is active"
        ::= { filterEntry 43 }

    filterSetIP OBJECT-TYPE
        SYNTAX          DisplayString(SIZE(0..16))
        MAX-ACCESS      read-create
        STATUS          current
        DESCRIPTION
            "Modify IP setting for this filter"
        ::= { filterEntry 44 }

    filterListTable OBJECT-TYPE
        SYNTAX          SEQUENCE OF FilterListEntry
        MAX-ACCESS      not-accessible
        STATUS          current
        DESCRIPTION
            "Filter list table for the Array"
        ::= { filter 5 }

    filterListEntry OBJECT-TYPE
        SYNTAX          FilterListEntry
        MAX-ACCESS      not-accessible
        STATUS          current
        DESCRIPTION
            "Filter list table entry"
        INDEX       { filterListIndex }
        ::= { filterListTable 1 }

    FilterListEntry ::= SEQUENCE {
        filterListIndex             Integer32,
        filterListName              DisplayString,
        filterListEnable            INTEGER,
        filterListLength            Integer32,
        filterListReset             INTEGER,
        filterListRowStatus         RowStatus
    }

    filterListIndex OBJECT-TYPE
        SYNTAX          Integer32
        MAX-ACCESS      not-accessible
        STATUS          current
        DESCRIPTION
            "Filter list table index"
        ::= { filterListEntry 1 }

    filterListName OBJECT-TYPE
        SYNTAX          DisplayString(SIZE(1..20))
        MAX-ACCESS      read-create
        STATUS          current
        DESCRIPTION
            "Filter list name"
        ::= { filterListEntry 2 }

    filterListEnable OBJECT-TYPE
        SYNTAX          INTEGER { disable(0), enable(1) }
        MAX-ACCESS      read-create
        STATUS          current
        DESCRIPTION
            "Enable/disable filter list"
        ::= { filterListEntry 3 }

    filterListLength OBJECT-TYPE
        SYNTAX          Integer32
        MAX-ACCESS      read-only
        STATUS          current
        DESCRIPTION
            "Number of filters in filter list"
        ::= { filterListEntry 4 }

    filterListReset OBJECT-TYPE
        SYNTAX          INTEGER { reset(1) }
        MAX-ACCESS      read-create
        STATUS          current
        DESCRIPTION
            "Delete all filters from filter list"
        ::= { filterListEntry 5 }

    filterListRowStatus OBJECT-TYPE
        SYNTAX          RowStatus
        MAX-ACCESS      read-create
        STATUS          current
        DESCRIPTION
            "Status of the filter list row entry"
        ::= { filterListEntry 6 }

    filterStateful OBJECT-TYPE
        SYNTAX          INTEGER { disable(0), enable(1) }
        MAX-ACCESS      read-write
        STATUS          current
        DESCRIPTION
            "Enable or disable stateful filtering"
        ::= { filter 6 }

    filterTrackApps OBJECT-TYPE
        SYNTAX          INTEGER { disable(0), enable(1) }
        MAX-ACCESS      read-write
        STATUS          current
        DESCRIPTION
            "Enable or disable application tracking"
        ::= { filter 7 }

    filterAppTable OBJECT-TYPE
        SYNTAX          SEQUENCE OF FilterAppEntry
        MAX-ACCESS      not-accessible
        STATUS          current
        DESCRIPTION
            "Filter application table for the Array"
        ::= { filter 8 }

    filterAppEntry OBJECT-TYPE
        SYNTAX          FilterAppEntry
        MAX-ACCESS      not-accessible
        STATUS          current
        DESCRIPTION
            "Filter application table entry"
        INDEX       { filterAppIndex }
        ::= { filterAppTable 1 }

    FilterAppEntry ::= SEQUENCE {
        filterAppIndex                 Integer32,
        filterAppGuid                  DisplayString,
        filterAppCategory              DisplayString,
        filterAppDescription           DisplayString
    }

    filterAppIndex OBJECT-TYPE
        SYNTAX          Integer32
        MAX-ACCESS      not-accessible
        STATUS          current
        DESCRIPTION
            "Filter application table index"
        ::= { filterAppEntry 1 }

    filterAppGuid OBJECT-TYPE
        SYNTAX          DisplayString
        MAX-ACCESS      read-only
        STATUS          current
        DESCRIPTION
            "Filter application global unique identifier"
        ::= { filterAppEntry 2 }

    filterAppCategory OBJECT-TYPE
        SYNTAX          DisplayString
        MAX-ACCESS      read-only
        STATUS          current
        DESCRIPTION
            "Filter application category global unique identifier"
        ::= { filterAppEntry 3 }

    filterAppDescription OBJECT-TYPE
        SYNTAX          DisplayString
        MAX-ACCESS      read-only
        STATUS          current
        DESCRIPTION
            "Filter application description"
        ::= { filterAppEntry 4 }

    filterAppCatTable OBJECT-TYPE
        SYNTAX          SEQUENCE OF FilterAppCatEntry
        MAX-ACCESS      not-accessible
        STATUS          current
        DESCRIPTION
            "Filter application category table for the Array"
        ::= { filter 9 }

    filterAppCatEntry OBJECT-TYPE
        SYNTAX          FilterAppCatEntry
        MAX-ACCESS      not-accessible
        STATUS          current
        DESCRIPTION
            "Filter application category table entry"
        INDEX       { filterAppCatIndex }
        ::= { filterAppCatTable 1 }

    FilterAppCatEntry ::= SEQUENCE {
        filterAppCatIndex                 Integer32,
        filterAppCatGuid                  DisplayString,
        filterAppCatDescription           DisplayString
    }

    filterAppCatIndex OBJECT-TYPE
        SYNTAX          Integer32
        MAX-ACCESS      not-accessible
        STATUS          current
        DESCRIPTION
            "Filter application category table index"
        ::= { filterAppCatEntry 1 }

    filterAppCatGuid OBJECT-TYPE
        SYNTAX          DisplayString
        MAX-ACCESS      read-only
        STATUS          current
        DESCRIPTION
            "Filter application category global unique identifier"
        ::= { filterAppCatEntry 2 }

    filterAppCatDescription OBJECT-TYPE
        SYNTAX          DisplayString
        MAX-ACCESS      read-only
        STATUS          current
        DESCRIPTION
            "Filter application category description"
        ::= { filterAppCatEntry 3 }

    filterAppListTable OBJECT-TYPE
        SYNTAX          SEQUENCE OF FilterAppListEntry
        MAX-ACCESS      not-accessible
        STATUS          current
       DESCRIPTION
            "Filter Custom Application Lists"
        ::= { filter 10 }

    filterAppListEntry OBJECT-TYPE
        SYNTAX          FilterAppListEntry
        MAX-ACCESS      not-accessible
        STATUS          current
        DESCRIPTION
            "Filter Custom Application Lists table entry"
        INDEX       { filterAppListIndex }
        ::= { filterAppListTable 1 }

    FilterAppListEntry ::= SEQUENCE {
        filterAppListIndex      Integer32,
        filterAppListGuid       DisplayString,
        filterAppListDesc       DisplayString,
        filterAppListRowStatus     RowStatus
        }

    filterAppListIndex OBJECT-TYPE 
        SYNTAX          Integer32
        MAX-ACCESS      not-accessible
        STATUS          current
        DESCRIPTION     
            "Filter Custom Application List Index"
        ::= { filterAppListEntry 1 }

    filterAppListGuid OBJECT-TYPE
        SYNTAX          DisplayString
        MAX-ACCESS      read-create
        STATUS          current
        DESCRIPTION
            "Filter Custom Application List GUID"
        ::= { filterAppListEntry 2 }

    filterAppListDesc OBJECT-TYPE
        SYNTAX          DisplayString
        MAX-ACCESS      read-create
        STATUS          current
        DESCRIPTION
            "Filter Custom Application List Description"
        ::= { filterAppListEntry 3 }        
    
    filterAppListRowStatus OBJECT-TYPE
        SYNTAX          RowStatus
        MAX-ACCESS      read-create
        STATUS          current
        DESCRIPTION
            "Filter Custom Application List Row Status"
        ::= { filterAppListEntry 4 }



    appListMemberTable OBJECT-TYPE
        SYNTAX          SEQUENCE OF AppListMemberEntry
        MAX-ACCESS      not-accessible
        STATUS          current
       DESCRIPTION
            "Filter Custom Application Lists Members"
        ::= { filter 11 }

    appListMemberEntry OBJECT-TYPE
        SYNTAX          AppListMemberEntry
        MAX-ACCESS      not-accessible
        STATUS          current
        DESCRIPTION
            "Filter Custom Application Lists Member table entry"
        INDEX       { appListMemberIndex }
        ::= { appListMemberTable 1 }

    AppListMemberEntry ::= SEQUENCE {
        appListMemberIndex         Integer32,
        appListMemberGuid          DisplayString,
        appListMemberApp           DisplayString,
        appListMemberRowStatus     RowStatus
        }

    appListMemberIndex OBJECT-TYPE 
        SYNTAX          Integer32
        MAX-ACCESS      not-accessible
        STATUS          current
        DESCRIPTION     
            "Filter Custom Application List Member Index"
        ::= { appListMemberEntry 1 }

    appListMemberGuid OBJECT-TYPE
        SYNTAX          DisplayString
        MAX-ACCESS      read-only
        STATUS          current
        DESCRIPTION
            "Filter Custom Application List Member GUID"
        ::= { appListMemberEntry 2 }

    appListMemberApp OBJECT-TYPE
        SYNTAX          DisplayString
        MAX-ACCESS      read-create
        STATUS          current
        DESCRIPTION
            "Filter Custom Application List Member Application"
        ::= { appListMemberEntry 3 }        
    
    appListMemberRowStatus OBJECT-TYPE
        SYNTAX          RowStatus
        MAX-ACCESS      read-create
        STATUS          current
        DESCRIPTION
            "Filter Custom Application List Member Row Status"
        ::= { appListMemberEntry 4 }


--
-- INTERFACE
--

    iap         OBJECT IDENTIFIER ::= { interface 1 }
    ethernet    OBJECT IDENTIFIER ::= { interface 2 }
    console     OBJECT IDENTIFIER ::= { interface 3 }

--
-- INTERFACE IAP
--

    iapTable OBJECT-TYPE
        SYNTAX          SEQUENCE OF IapEntry
        MAX-ACCESS      not-accessible
        STATUS          current
        DESCRIPTION
            "Table of IAPs"
        ::= { iap 1 }

    iapEntry OBJECT-TYPE
        SYNTAX          IapEntry
        MAX-ACCESS      not-accessible
        STATUS          current
        DESCRIPTION
            "IAP table entry"
        INDEX       { iapIndex }
        ::= { iapTable 1 }

    IapEntry ::= SEQUENCE {
        iapIndex             Integer32,
        iapName              DisplayString,
        iapMacAddress        DisplayString,
        iapNumStations       Integer32,
        iapEnable            INTEGER,
        iapCellSize          INTEGER,
        iapTxPwr             Integer32,
        iapRxThreshold       Integer32,
        iapChannel           Integer32,
        iapDot11Mode         INTEGER,
        iapAntenna           INTEGER,
        iapDescription       DisplayString,
        iapWdsClientLink     Integer32,
        iapWdsHostLink       Integer32,
        iapChannelBondMode   INTEGER,
        iapBondedChannel     Integer32,
        iapMaxStationsHour   Integer32,
        iapMaxStationsDay    Integer32,
        iapMaxStationsWeek   Integer32,
        iapMaxStationsMonth  Integer32,
        iapMaxStationsYear   Integer32,
        iapChannelMode       INTEGER,
        iapWifiMode          INTEGER,
        iapPresent           INTEGER,
        iapWdsLinkDistance   Integer32,
        iapResetsMonitor     Counter64,
        iapResetsBeacon      Counter64,
        iapResetsPhy         Counter64,
        iapResetsMac         Counter64,
        iapResetsSystem      Counter64,
        iapSpatialStreams    INTEGER,
        iapChannelBond80Mhz  INTEGER,
        iapBondedChannelList DisplayString,
        iapType              INTEGER,
        iapChannelBond160Mhz INTEGER
    }

    iapIndex OBJECT-TYPE
        SYNTAX          Integer32
        MAX-ACCESS      not-accessible
        STATUS          current
        DESCRIPTION
            "IAP table index"
        ::= { iapEntry 1 }

    iapName OBJECT-TYPE
        SYNTAX          DisplayString
        MAX-ACCESS      read-only
        STATUS          current
        DESCRIPTION
            "IAP name"
        ::= { iapEntry 2 }

    iapMacAddress OBJECT-TYPE
        SYNTAX          DisplayString
        MAX-ACCESS      read-only
        STATUS          current
        DESCRIPTION
            "IAP Mac address"
        ::= { iapEntry 3 }

    iapNumStations OBJECT-TYPE
        SYNTAX          Integer32
        MAX-ACCESS      read-only
        STATUS          current
        DESCRIPTION
            "Number of associated stations per IAP"
        ::= { iapEntry 4 }

    iapEnable OBJECT-TYPE
        SYNTAX          INTEGER { down(0), up(1) }
        MAX-ACCESS      read-write
        STATUS          current
        DESCRIPTION
            "Bring IAP up or down"
        ::= { iapEntry 5 }

    iapCellSize OBJECT-TYPE
        SYNTAX          INTEGER { manual(0), small(1), medium(2), large(3),
                                  max(4), auto(5), monitor(6) }
        MAX-ACCESS      read-write
        STATUS          current
        DESCRIPTION
            "Set up RF cell size base on Tx pwr and Rx Threshold"
        ::= { iapEntry 6 }

    iapTxPwr OBJECT-TYPE
        SYNTAX          Integer32(-15..20)
        MAX-ACCESS      read-write
        STATUS          current
        DESCRIPTION
            "Maximum Tx power output from radio"
        ::= { iapEntry 7 }

    iapRxThreshold OBJECT-TYPE
        SYNTAX          Integer32(-100..0)
        MAX-ACCESS      read-write
        STATUS          current
        DESCRIPTION
            "Rx (deferred) threshold setting"
        ::= { iapEntry 8 }

    iapChannel OBJECT-TYPE
        SYNTAX          Integer32(0..256)
        MAX-ACCESS      read-write
        STATUS          current
        DESCRIPTION
            "Set channel (0 to set monitor mode for abg2 only)"
        ::= { iapEntry 9 }

    iapAntenna OBJECT-TYPE
        SYNTAX          INTEGER { internal(1), external(2), omni(3) }
        MAX-ACCESS      read-write
        STATUS          current
        DESCRIPTION
            "Set antenna (abg only radios)"
        ::= { iapEntry 10 }

    iapDot11Mode OBJECT-TYPE
        SYNTAX          INTEGER { dot11a(0), dot11g(1), monitor(2) }
        MAX-ACCESS      read-write
        STATUS          current
        DESCRIPTION
            "Set 802.11 mode (band), where dot11a mode is 5GHz band and dot11g mode is 2.4GHz band (abg only radios)"
        ::= { iapEntry 11 }

    iapDescription OBJECT-TYPE
        SYNTAX          DisplayString(SIZE(0..50))
        MAX-ACCESS      read-write
        STATUS          current
        DESCRIPTION
            "IAP description"
        ::= { iapEntry 12 }

    iapWdsClientLink OBJECT-TYPE
        SYNTAX          Integer32(0..4)
        MAX-ACCESS      read-write
        STATUS          current
        DESCRIPTION
            "Assign this IAP to a WDS client link (1-4), 0 means no link"
        ::= { iapEntry 13 }

    iapWdsHostLink OBJECT-TYPE
        SYNTAX          Integer32(0..4)
        MAX-ACCESS      read-write
        STATUS          current
        DESCRIPTION
            "Assign this IAP to a WDS host link (1-4), 0 means no link"
        ::= { iapEntry 14 }

    iapChannelBondMode OBJECT-TYPE
        SYNTAX          INTEGER { minus1(-1), off(0), plus1(1), auto(2) }
        MAX-ACCESS      read-write
        STATUS          current
        DESCRIPTION
            "Channel bonding 40Mhz setting (802.11n)"
        ::= { iapEntry 15 }

    iapBondedChannel OBJECT-TYPE
        SYNTAX          Integer32
        MAX-ACCESS      read-only
        STATUS          current
        DESCRIPTION
            "Bonded channel (802.11n)"
        ::= { iapEntry 16 }

    iapMaxStationsHour OBJECT-TYPE
        SYNTAX          Integer32
        MAX-ACCESS      read-only
        STATUS          current
        DESCRIPTION
            "Maximum number of associated stations over last hour"
        ::= { iapEntry 17 }

    iapMaxStationsDay OBJECT-TYPE
        SYNTAX          Integer32
        MAX-ACCESS      read-only
        STATUS          current
        DESCRIPTION
            "Maximum number of associated stations over last day"
        ::= { iapEntry 18 }

    iapMaxStationsWeek OBJECT-TYPE
        SYNTAX          Integer32
        MAX-ACCESS      read-only
        STATUS          current
        DESCRIPTION
            "Maximum number of associated stations over last week"
        ::= { iapEntry 19 }

    iapMaxStationsMonth OBJECT-TYPE
        SYNTAX          Integer32
        MAX-ACCESS      read-only
        STATUS          current
        DESCRIPTION
            "Maximum number of associated stations over last month"
        ::= { iapEntry 20 }

    iapMaxStationsYear OBJECT-TYPE
        SYNTAX          Integer32
        MAX-ACCESS      read-only
        STATUS          current
        DESCRIPTION
            "Maximum number of associated stations over last year"
        ::= { iapEntry 21 }

    iapChannelMode OBJECT-TYPE
        SYNTAX          INTEGER { default(0), manual(1), auto(2), radar(3),
                                  locked(4), monitor(5), timeshare(6) }
        MAX-ACCESS      read-write
        STATUS          current
        DESCRIPTION
            "Channel mode (on set, use 4 to lock, 0 to unlock channel)"
        ::= { iapEntry 22 }

    iapWifiMode OBJECT-TYPE
        SYNTAX          INTEGER { dot11a(1), dot11b(2), dot11ab(3), dot11g(4),
                                  dot11ag(5), dot11bg(6), dot11abg(7), dot11n(8),
                                  dot11an(9), dot11bn(10), dot11abn(11), dot11gn(12),
                                  dot11agn(13), dot11bgn(14), dot11abgn(15),
                                  dot11ac(16), dot11nac(24), dot11anac(25), dot11abgnac(31) }
        MAX-ACCESS      read-write
        STATUS          current
        DESCRIPTION
            "Wifi mode"
        ::= { iapEntry 23 }

    iapPresent OBJECT-TYPE
        SYNTAX          INTEGER { not-present(0), present(1) }
        MAX-ACCESS      read-only
        STATUS          current
        DESCRIPTION
            "Indicates whether IAP slot is populated"
        ::= { iapEntry 24 }

    iapWdsLinkDistance OBJECT-TYPE
        SYNTAX          Integer32(0..30)
        MAX-ACCESS      read-write
        STATUS          current
        DESCRIPTION
            "WDS link distance (in miles)"
        ::= { iapEntry 25 }

    iapResetsMonitor OBJECT-TYPE
        SYNTAX          Counter64
        MAX-ACCESS      read-only
        STATUS          current
        DESCRIPTION
            "Number of monitor radio resets"
        ::= { iapEntry 26 }

    iapResetsBeacon OBJECT-TYPE
        SYNTAX          Counter64
        MAX-ACCESS      read-only
        STATUS          current
        DESCRIPTION
            "Number of interface beacon resets"
        ::= { iapEntry 27 }

    iapResetsPhy OBJECT-TYPE
        SYNTAX          Counter64
        MAX-ACCESS      read-only
        STATUS          current
        DESCRIPTION
            "Number of interface PHY resets"
        ::= { iapEntry 28 }

    iapResetsMac OBJECT-TYPE
        SYNTAX          Counter64
        MAX-ACCESS      read-only
        STATUS          current
        DESCRIPTION
            "Number of interface MAC resets"
        ::= { iapEntry 29 }

    iapResetsSystem OBJECT-TYPE
        SYNTAX          Counter64
        MAX-ACCESS      read-only
        STATUS          current
        DESCRIPTION
            "Number of system resets"
        ::= { iapEntry 30 }

    iapSpatialStreams OBJECT-TYPE
        SYNTAX          INTEGER { not-present(0), type-1x1(1), type-2x2(2), type-2x3(3), type-3x3(4), type-4x4(5) }
        MAX-ACCESS      read-only
        STATUS          current
        DESCRIPTION
            "Number of spatial streams on the IAP"
        ::= { iapEntry 31 }

    iapChannelBond80Mhz OBJECT-TYPE
        SYNTAX          INTEGER { off(0), on(1) }
        MAX-ACCESS      read-write
        STATUS          current
        DESCRIPTION
            "Channel bonding 80Mhz setting"
        ::= { iapEntry 32 }

    iapBondedChannelList OBJECT-TYPE
        SYNTAX          DisplayString
        MAX-ACCESS      read-only
        STATUS          current
        DESCRIPTION
            "IAP Bonded Channel List"
        ::= { iapEntry 33 }

    iapType OBJECT-TYPE
        SYNTAX          INTEGER { not-present(0), unknown(1), dot11abgn(2), dot11abgnac(3), dot11an(4), dot11anac(5) }
        MAX-ACCESS      read-only
        STATUS          current
        DESCRIPTION
            "IAP type"
        ::= { iapEntry 34 }

    iapChannelBond160Mhz OBJECT-TYPE
        SYNTAX          INTEGER { off(0), on(1) }
        MAX-ACCESS      read-write
        STATUS          current
        DESCRIPTION
            "Channel bonding 160Mhz setting"
        ::= { iapEntry 35 }


    global      OBJECT IDENTIFIER ::= { iap 2 }
    global11a   OBJECT IDENTIFIER ::= { iap 3 }
    global11bg  OBJECT IDENTIFIER ::= { iap 4 }
    wds         OBJECT IDENTIFIER ::= { iap 5 }
    global11n   OBJECT IDENTIFIER ::= { iap 6 }
    global11ac  OBJECT IDENTIFIER ::= { iap 8 }

--
-- INTERFACE IAP GLOBAL
--

    globalIAPEnable OBJECT-TYPE
        SYNTAX          INTEGER { all-down(0), all-up(1) }
        MAX-ACCESS      read-write
        STATUS          current
        DESCRIPTION
            "Bring all IAPs up or down"
        ::= { global 1 }

    globalIAPCellSize OBJECT-TYPE
        SYNTAX          INTEGER { none(0), small(1), medium(2), large(3),
                                  max(4), auto(5), monitor(6) }
        MAX-ACCESS      read-write
        STATUS          current
        DESCRIPTION
            "Set up RF cell size base on Tx pwr and Rx Threshold"
        ::= { global 2 }

    globalIAPTxPwr OBJECT-TYPE
        SYNTAX          Integer32(-15..20)
        MAX-ACCESS      read-write
        STATUS          current
        DESCRIPTION
            "Maximum Tx power output from any radio"
        ::= { global 3 }

    globalIAPRxThreshold OBJECT-TYPE
        SYNTAX          Integer32(-100..0)
        MAX-ACCESS      read-write
        STATUS          current
        DESCRIPTION
            "Rx (deferred) threshold setting"
        ::= { global 4 }

    globalIAPBeaconRate OBJECT-TYPE
        SYNTAX          Integer32(100..1000)
        MAX-ACCESS      read-write
        STATUS          current
        DESCRIPTION
            "Time between beacons in kilo_microseconds"
        ::= { global 5 }

    globalIAPBeaconDTIM OBJECT-TYPE
        SYNTAX          Integer32(1..255)
        MAX-ACCESS      read-write
        STATUS          current
        DESCRIPTION
            "Number of beacons between DTIM being transmitted"
        ::= { global 6 }

    globalIAPLongRetry OBJECT-TYPE
        SYNTAX          Integer32(1..128)
        MAX-ACCESS      read-write
        STATUS          current
        DESCRIPTION
            "Long retry"
        ::= { global 7 }

    globalIAPShortRetry OBJECT-TYPE
        SYNTAX          Integer32(1..128)
        MAX-ACCESS      read-write
        STATUS          current
        DESCRIPTION
            "Short retry"
        ::= { global 8 }

    globalIAPMaxStations OBJECT-TYPE
        SYNTAX          Integer32(1..240)
        MAX-ACCESS      read-write
        STATUS          current
        DESCRIPTION
            "Limit the number of STA that can be associated per IAP"
        ::= { global 9 }

    globalIAPInactiveTime OBJECT-TYPE
        SYNTAX          Integer32(1..65535)
        MAX-ACCESS      read-write
        STATUS          current
        DESCRIPTION
            "Time, in seconds, without any activity before removing the client from the association table"
        ::= { global 10 }

    globalIAPReauthPeriod OBJECT-TYPE
        SYNTAX          Integer32(0..65535)
        MAX-ACCESS      read-write
        STATUS          current
        DESCRIPTION
            "Time (sec) between 802.1x re_authentication attempts"
        ::= { global 11 }

    globalIAPSta2Sta OBJECT-TYPE
        SYNTAX          INTEGER { forward(0), block(1) }
        MAX-ACCESS      read-write
        STATUS          current
        DESCRIPTION
            "Block or forward intra-Array STA to STA traffic"
        ::= { global 12 }

    globalMgmt OBJECT-TYPE
        SYNTAX          INTEGER { disable(0), enable(1) }
        MAX-ACCESS      read-write
        STATUS          current
        DESCRIPTION
            "Enable management on the WLAN interfaces"
        ::= { global 13 }

    leds          OBJECT IDENTIFIER ::= { global 14 }
    autoChannel   OBJECT IDENTIFIER ::= { global 15 }
    rogueDetect   OBJECT IDENTIFIER ::= { global 16 }
    fastRoaming   OBJECT IDENTIFIER ::= { global 17 }
    autoCell      OBJECT IDENTIFIER ::= { global 24 }
    ids           OBJECT IDENTIFIER ::= { global 33 }
    rfMonitor     OBJECT IDENTIFIER ::= { global 40 }

    globalLoadBalancing OBJECT-TYPE
        SYNTAX          INTEGER { disable(0), enable(2) }
        MAX-ACCESS      read-write
        STATUS          current
        DESCRIPTION
            "Enable/disable load balancing across IAPs"
        ::= { global 18 }

    globalCountryCode OBJECT-TYPE
        SYNTAX          INTEGER { not-set(0), united-states(1), canada(2),
                                  australia(3), new-zealand(4), austria(5),
                                  belgium(6), denmark(7), finland(8),
                                  france(9), germany(10), hungary(11),
                                  ireland(12), italy(13), luxembourg(14),
                                  netherlands(15), norway(16), poland(17),
                                  portugal(18), slovenia(19), spain(20),
                                  sweden(21), switzerland(22), united-kingdom(23),
                                  japan(24), united-states-ext(25), mexico(26),
                                  thailand(27), greece(28), israel(29),
                                  south-africa(30), brazil(31), india(32),
                                  singapore(33), malaysia(34), korea(35),
                                  hong-kong(36), china(37), macao (38),
                                  united-states-outdoor (39), united-status-weather-radar (40),
                                  russia (41), united-states-non-dfs (42),
                                  united-arab-emirates (43), argentina (44), bahrain (45),
                                  brunei (46), bahamas (47), chile (48),
                                  colombia (49), dominican-republic (50), egypt (51),
                                  indonesia (52), kuwait (53), lebanon (54),
                                  oman (55), peru (56), philippines (57),
                                  qatar (58), saudi-arabia (59), taiwan (60),
                                  turkey (61), trinidad (62), ukraine (63),
                                  venezuela (64) }
        MAX-ACCESS      read-write
        STATUS          current
        DESCRIPTION
            "Country code"
        ::= { global 19 }

    globalSharpCell OBJECT-TYPE
        SYNTAX          INTEGER { disable(0), enable(1) }
        MAX-ACCESS      read-write
        STATUS          current
        DESCRIPTION
            "Enable/disable sharp cell TX power shaping"
        ::= { global 20 }

    globalIAPMaxPhones OBJECT-TYPE
        SYNTAX          Integer32(0..16)
        MAX-ACCESS      read-write
        STATUS          current
        DESCRIPTION
            "Limit the number of phones that can be associated per IAP. Note this is not used and essentially deprecated."
        ::= { global 21 }

    globalNumStations OBJECT-TYPE
        SYNTAX          Integer32
        MAX-ACCESS      read-only
        STATUS          current
        DESCRIPTION
            "Number of stations associated with array"
        ::= { global 22 }

    globalBroadcastRates OBJECT-TYPE
        SYNTAX          INTEGER { standard(0), optimized(1) }
        MAX-ACCESS      read-write
        STATUS          current
        DESCRIPTION
            "Select standard or optimized broadcast rates"
        ::= { global 23 }

    globalPublicSafety OBJECT-TYPE
        SYNTAX          INTEGER { disable(0), enable(1) }
        MAX-ACCESS      read-write
        STATUS          current
        DESCRIPTION
            "Enable/disable public safety band"
        ::= { global 25 }

    globalDot11hSupport OBJECT-TYPE
        SYNTAX          INTEGER { disable(0), enable(1) }
        MAX-ACCESS      read-write
        STATUS          current
        DESCRIPTION
            "Enable/disable support for 802.11h beacons"
        ::= { global 26 }

    globalLoopbackTest OBJECT-TYPE
        SYNTAX          INTEGER { disabled(0), alert-only(1),
                                  repair-without-reboot(2), reboot-allowed(3) }
        MAX-ACCESS      read-write
        STATUS          current
        DESCRIPTION
            "IAP radio assurance mode"
        ::= { global 27 }

    globalArpFilter OBJECT-TYPE
        SYNTAX          INTEGER { disable(0), passthru(1), proxy(2) }
        MAX-ACCESS      read-write
        STATUS          current
        DESCRIPTION
            "Enable/disable ARP filtering"
        ::= { global 28 }

    globalIAPChannelReset OBJECT-TYPE
        SYNTAX          INTEGER { reset(1) }
        MAX-ACCESS      read-write
        STATUS          current
        DESCRIPTION
            "Reset all channels back to factory defaults"
        ::= { global 29 }

    globalWfaMode OBJECT-TYPE
        SYNTAX          INTEGER { disable(0), enable(1) }
        MAX-ACCESS      read-write
        STATUS          current
        DESCRIPTION
            "Enable/disable WiFi Alliance mode"
        ::= { global 30 }

    globalMaxStations OBJECT-TYPE
        SYNTAX          Integer32(1..3840)
        MAX-ACCESS      read-write
        STATUS          current
        DESCRIPTION
            "Maximum number of associated stations per array"
        ::= { global 31 }

    globalMulticastMode OBJECT-TYPE
        SYNTAX          INTEGER { standard(0), convert(1), snoop(2), prune(3) }
        MAX-ACCESS      read-write
        STATUS          current
        DESCRIPTION
            "Select multicast mode"
        ::= { global 32 }

    globalAutoBandEnable OBJECT-TYPE
        SYNTAX          INTEGER { enable(1) }
        MAX-ACCESS      read-write
        STATUS          current
        DESCRIPTION
            "Automatically assign bands (2.4GHz or 5GHz) to all IAPs"
        ::= { global 34 }

    globalWmmPowerSave OBJECT-TYPE
        SYNTAX          INTEGER { disable(0), enable(1) }
        MAX-ACCESS      read-write
        STATUS          current
        DESCRIPTION
            "Enable/disable WMM power save mode"
        ::= { global 35 }

    globalDscpMappingMode OBJECT-TYPE
        SYNTAX          INTEGER { disable(0), enable(1) }
        MAX-ACCESS      read-write
        STATUS          current
        DESCRIPTION
            "Enable/disable DSCP to QoS mapping"
        ::= { global 36 }

    globalDscpMappingTable OBJECT-TYPE
        SYNTAX          SEQUENCE OF GlobalDscpMappingEntry
        MAX-ACCESS      not-accessible
        STATUS          current
        DESCRIPTION
            "DSCP to QoS mapping"
        ::= { global 37 }

    globalDscpMappingEntry OBJECT-TYPE
        SYNTAX          GlobalDscpMappingEntry
        MAX-ACCESS      not-accessible
        STATUS          current
        DESCRIPTION
            "DSCP to QoS mapping entry"
        INDEX       { globalDscpMappingIndex }
        ::= { globalDscpMappingTable 1 }

    GlobalDscpMappingEntry ::= SEQUENCE {
        globalDscpMappingIndex      Integer32,
        globalDscpMappingDscp       Integer32,
        globalDscpMappingQos        Integer32
    }

    globalDscpMappingIndex OBJECT-TYPE
        SYNTAX          Integer32
        MAX-ACCESS      not-accessible
        STATUS          current
        DESCRIPTION
            "DSCP to QoS mapping index"
        ::= { globalDscpMappingEntry 1 }

    globalDscpMappingDscp OBJECT-TYPE
        SYNTAX          Integer32
        MAX-ACCESS      read-only
        STATUS          current
        DESCRIPTION
            "DSCP value mapped"
        ::= { globalDscpMappingEntry 2 }

    globalDscpMappingQos OBJECT-TYPE
        SYNTAX          Integer32(0..3)
        MAX-ACCESS      read-write
        STATUS          current
        DESCRIPTION
            "QoS setting"
        ::= { globalDscpMappingEntry 3 }

    globalMulticastExcludeTable OBJECT-TYPE
        SYNTAX          SEQUENCE OF GlobalMulticastExcludeEntry
        MAX-ACCESS      not-accessible
        STATUS          current
        DESCRIPTION
            "Multicast conversion exclude list"
        ::= { global 38 }

    globalMulticastExcludeEntry OBJECT-TYPE
        SYNTAX          GlobalMulticastExcludeEntry
        MAX-ACCESS      not-accessible
        STATUS          current
        DESCRIPTION
            "Multicast conversion exclude list entry"
        INDEX       { globalMulticastExcludeIndex }
        ::= { globalMulticastExcludeTable 1 }

    GlobalMulticastExcludeEntry ::= SEQUENCE {
        globalMulticastExcludeIndex         Integer32,
        globalMulticastExcludeIpAddress     IpAddress,
        globalMulticastExcludeRowStatus     RowStatus
    }

    globalMulticastExcludeIndex OBJECT-TYPE
        SYNTAX          Integer32
        MAX-ACCESS      not-accessible
        STATUS          current
        DESCRIPTION
            "Multicast conversion exclude list Index"
        ::= { globalMulticastExcludeEntry 1 }

    globalMulticastExcludeIpAddress OBJECT-TYPE
        SYNTAX          IpAddress
        MAX-ACCESS      read-create
        STATUS          current
        DESCRIPTION
            "Multicast IP address excluded from conversion"
        ::= { globalMulticastExcludeEntry 2 }

    globalMulticastExcludeRowStatus OBJECT-TYPE
        SYNTAX          RowStatus
        MAX-ACCESS      read-create
        STATUS          current
        DESCRIPTION
            "Status of the multicast conversion exclude list row entry"
        ::= { globalMulticastExcludeEntry 3 }

    globalMulticastExcludeTableReset OBJECT-TYPE
        SYNTAX          INTEGER { reset(1) }
        MAX-ACCESS      read-write
        STATUS          current
        DESCRIPTION
            "Reset multicast conversion exclude list"
        ::= { global 39 }

    globalExtractStaInfoTable OBJECT-TYPE
        SYNTAX          SEQUENCE OF GlobalExtractStaInfoEntry
        MAX-ACCESS      not-accessible
        STATUS          current
        DESCRIPTION
            "Station information to be extracted table"
        ::= { global 41 }

    globalExtractStaInfoEntry OBJECT-TYPE
        SYNTAX          GlobalExtractStaInfoEntry
        MAX-ACCESS      not-accessible
        STATUS          current
        DESCRIPTION
            "Station information to be extracted table entry"
        INDEX       { globalExtractStaInfoIndex }
        ::= { globalExtractStaInfoTable 1 }

    GlobalExtractStaInfoEntry ::= SEQUENCE {
        globalExtractStaInfoIndex       Integer32,
        globalExtractStaInfoType        DisplayString,
        globalExtractStaInfoStatus      INTEGER
    }

    globalExtractStaInfoIndex OBJECT-TYPE
        SYNTAX          Integer32
        MAX-ACCESS      not-accessible
        STATUS          current
        DESCRIPTION
            "Station information to be extracted table index"
        ::= { globalExtractStaInfoEntry 1 }

    globalExtractStaInfoType OBJECT-TYPE
        SYNTAX          DisplayString
        MAX-ACCESS      read-only
        STATUS          current
        DESCRIPTION
            "Type of station information to be extracted"
        ::= { globalExtractStaInfoEntry 2 }

    globalExtractStaInfoStatus OBJECT-TYPE
        SYNTAX          INTEGER { disabled(0), enabled(1) }
        MAX-ACCESS      read-write
        STATUS          current
        DESCRIPTION
            "Enable/disable station information to be extracted"
        ::= { globalExtractStaInfoEntry 3 }

    globalStaAuthTimeout OBJECT-TYPE
        SYNTAX          Integer32(60..65535)
        MAX-ACCESS      read-write
        STATUS          current
        DESCRIPTION
            "Time to complete 802.1x authentication (seconds)"
        ::= { global 42 }

    globalIPv6Filter OBJECT-TYPE
        SYNTAX          INTEGER { disable(0), enable(1) }
        MAX-ACCESS      read-write
        STATUS          current
        DESCRIPTION
            "Enable/disable IPv6 packet filtering"
        ::= { global 43 }

    globalMulticastForwardingTable OBJECT-TYPE
        SYNTAX          SEQUENCE OF GlobalMulticastForwardingEntry
        MAX-ACCESS      not-accessible
        STATUS          current
        DESCRIPTION
            "Multicast conversion forwarding list"
        ::= { global 44 }

    globalMulticastForwardingEntry OBJECT-TYPE
        SYNTAX          GlobalMulticastForwardingEntry
        MAX-ACCESS      not-accessible
        STATUS          current
        DESCRIPTION
            "Multicast conversion forwarding list entry"
        INDEX       { globalMulticastForwardingIndex }
        ::= { globalMulticastForwardingTable 1 }

    GlobalMulticastForwardingEntry ::= SEQUENCE {
        globalMulticastForwardingIndex         Integer32,
        globalMulticastForwardingIpAddress     IpAddress,
        globalMulticastForwardingRowStatus     RowStatus
    }

    globalMulticastForwardingIndex OBJECT-TYPE
        SYNTAX          Integer32
        MAX-ACCESS      not-accessible
        STATUS          current
        DESCRIPTION
            "Multicast conversion forwarding list Index"
        ::= { globalMulticastForwardingEntry 1 }

    globalMulticastForwardingIpAddress OBJECT-TYPE
        SYNTAX          IpAddress
        MAX-ACCESS      read-create
        STATUS          current
        DESCRIPTION
            "Multicast IP address forwarding from conversion"
        ::= { globalMulticastForwardingEntry 2 }

    globalMulticastForwardingRowStatus OBJECT-TYPE
        SYNTAX          RowStatus
        MAX-ACCESS      read-create
        STATUS          current
        DESCRIPTION
            "Status of the multicast conversion forwarding list row entry"
        ::= { globalMulticastForwardingEntry 3 }

    globalMulticastForwardingTableReset OBJECT-TYPE
        SYNTAX          INTEGER { reset(1) }
        MAX-ACCESS      read-write
        STATUS          current
        DESCRIPTION
            "Reset multicast conversion forwarding list"
        ::= { global 45 }

    globalMulticastVlanForwardingTable OBJECT-TYPE
        SYNTAX          SEQUENCE OF GlobalMulticastVlanForwardingEntry
        MAX-ACCESS      not-accessible
        STATUS          current
        DESCRIPTION
            "Multicast conversion vlan forwarding list"
        ::= { global 46 }

    globalMulticastVlanForwardingEntry OBJECT-TYPE
        SYNTAX          GlobalMulticastVlanForwardingEntry
        MAX-ACCESS      not-accessible
        STATUS          current
        DESCRIPTION
            "Multicast conversion vlan forwarding list entry"
        INDEX       { globalMulticastVlanForwardingIndex }
        ::= { globalMulticastVlanForwardingTable 1 }

    GlobalMulticastVlanForwardingEntry ::= SEQUENCE {
        globalMulticastVlanForwardingIndex         Integer32,
        globalMulticastVlanForwardingVlanNumber    Integer32,
        globalMulticastVlanForwardingRowStatus     RowStatus
    }

    globalMulticastVlanForwardingIndex OBJECT-TYPE
        SYNTAX          Integer32
        MAX-ACCESS      not-accessible
        STATUS          current
        DESCRIPTION
            "Multicast conversion vlan forwarding list Index"
        ::= { globalMulticastVlanForwardingEntry 1 }

    globalMulticastVlanForwardingVlanNumber OBJECT-TYPE
        SYNTAX          Integer32
        MAX-ACCESS      read-create
        STATUS          current
        DESCRIPTION
            "Multicast IP vlan forwarding from conversion"
        ::= { globalMulticastVlanForwardingEntry 2 }

    globalMulticastVlanForwardingRowStatus OBJECT-TYPE
        SYNTAX          RowStatus
        MAX-ACCESS      read-create
        STATUS          current
        DESCRIPTION
            "Status of the multicast conversion vlan forwarding list row entry"
        ::= { globalMulticastVlanForwardingEntry 3 }

    globalMulticastVlanForwardingTableReset OBJECT-TYPE
        SYNTAX          INTEGER { reset(1) }
        MAX-ACCESS      read-write
        STATUS          current
        DESCRIPTION
            "Reset multicast conversion vlan forwarding list"
        ::= { global 47 }

    globalMulticastDnsFilteringTable OBJECT-TYPE
        SYNTAX          SEQUENCE OF GlobalMulticastDnsFilteringEntry
        MAX-ACCESS      not-accessible
        STATUS          current
        DESCRIPTION
            "Multicast DNS filtering list"
        ::= { global 48 }

    globalMulticastDnsFilteringEntry OBJECT-TYPE
        SYNTAX          GlobalMulticastDnsFilteringEntry
        MAX-ACCESS      not-accessible
        STATUS          current
        DESCRIPTION
            "Multicast DNS filtering list entry"
        INDEX       { globalMulticastDnsFilteringIndex }
        ::= { globalMulticastDnsFilteringTable 1 }

    GlobalMulticastDnsFilteringEntry ::= SEQUENCE {
        globalMulticastDnsFilteringIndex         Integer32,
        globalMulticastDnsFilteringName          DisplayString,
        globalMulticastDnsFilteringRowStatus     RowStatus
    }

    globalMulticastDnsFilteringIndex OBJECT-TYPE
        SYNTAX          Integer32
        MAX-ACCESS      not-accessible
        STATUS          current
        DESCRIPTION
            "Multicast DNS filtering list Index"
        ::= { globalMulticastDnsFilteringEntry 1 }

    globalMulticastDnsFilteringName OBJECT-TYPE
        SYNTAX          DisplayString(SIZE(1..24))
        MAX-ACCESS      read-create
        STATUS          current
        DESCRIPTION
            "Multicast DNS filtering list"
        ::= { globalMulticastDnsFilteringEntry 2 }

    globalMulticastDnsFilteringRowStatus OBJECT-TYPE
        SYNTAX          RowStatus
        MAX-ACCESS      read-create
        STATUS          current
        DESCRIPTION
            "Status of the multicast DNS filtering list row entry"
        ::= { globalMulticastDnsFilteringEntry 3 }

    globalMulticastDnsFilteringTableReset OBJECT-TYPE
        SYNTAX          INTEGER { reset(1) }
        MAX-ACCESS      read-write
        STATUS          current
        DESCRIPTION
            "Reset multicast DNS filtering list"
        ::= { global 49 }

    globalDot11kSupport OBJECT-TYPE
        SYNTAX          INTEGER { disable(0), enable(1) }
        MAX-ACCESS      read-write
        STATUS          current
        DESCRIPTION
            "Enable/disable support for 802.11k beacons"
        ::= { global 50 }

	globalDot11wProtectedManagement OBJECT-TYPE
        SYNTAX          INTEGER { disable(0), enable(1) }
        MAX-ACCESS      read-write
        STATUS          current
        DESCRIPTION
            "Enable/disable support for 802.11w Protected Management"
        ::= { global 51 }

    globalExtractIpAddrDhcpPeriod OBJECT-TYPE
        SYNTAX          Integer32(0..300)
        MAX-ACCESS      read-write
        STATUS          current
        DESCRIPTION
            "Station IP address extraction via DHCP period"
        ::= { global 52 }

--
-- INTERFACE IAP GLOBAL LEDS
--

    ledsEnable OBJECT-TYPE
        SYNTAX          INTEGER { disable(0), iapUp(1), associated(2) }
        MAX-ACCESS      read-write
        STATUS          current
        DESCRIPTION
            "Enable/Disable LED operations"
        ::= { leds 1 }

    ledsActivityTable OBJECT-TYPE
        SYNTAX          SEQUENCE OF LedsActivityEntry
        MAX-ACCESS      not-accessible
        STATUS          current
        DESCRIPTION
            "LED activity table"
        ::= { leds 2 }

    ledsActivityEntry OBJECT-TYPE
        SYNTAX          LedsActivityEntry
        MAX-ACCESS      not-accessible
        STATUS          current
        DESCRIPTION
            "LED activity table entry"
        INDEX       { ledsActivityIndex }
        ::= { ledsActivityTable 1 }

    LedsActivityEntry ::= SEQUENCE {
        ledsActivityIndex           Integer32,
        ledsActivityPacketType      DisplayString,
        ledsActivityStatus          INTEGER
    }

    ledsActivityIndex OBJECT-TYPE
        SYNTAX          Integer32
        MAX-ACCESS      not-accessible
        STATUS          current
        DESCRIPTION
            "LED activity table index"
        ::= { ledsActivityEntry 1 }

    ledsActivityPacketType OBJECT-TYPE
        SYNTAX          DisplayString
        MAX-ACCESS      read-only
        STATUS          current
        DESCRIPTION
            "Packet type"
        ::= { ledsActivityEntry 2 }

    ledsActivityStatus OBJECT-TYPE
        SYNTAX          INTEGER { disabled(0), enabled(1) }
        MAX-ACCESS      read-write
        STATUS          current
        DESCRIPTION
            "Enable/disable blinking"
        ::= { ledsActivityEntry 3 }

--
-- INTERFACE IAP GLOBAL AUTO CHANNEL
--

    autoChannelEnable OBJECT-TYPE
        SYNTAX          INTEGER { enable(1), negotiate(2) }
        MAX-ACCESS      read-write
        STATUS          current
        DESCRIPTION
            "Set to 1 to enable auto channel configuration, 2 to negotiate airtime with other arrays before enabling auto channel configuration"
        ::= { autoChannel 1 }

    autoChannelPowerUp OBJECT-TYPE
        SYNTAX          INTEGER { disable(0), enable(1) }
        MAX-ACCESS      read-write
        STATUS          current
        DESCRIPTION
            "Enable/disable auto channel configuration at power up"
        ::= { autoChannel 2 }

    autoChannelSchedule OBJECT-TYPE
        SYNTAX          DisplayString(SIZE(0..255))
        MAX-ACCESS      read-write
        STATUS          current
        DESCRIPTION
            "Times to run auto channel in 'hh:mm hh:mm ...' format"
        ::= { autoChannel 3 }

--
-- INTERFACE IAP GLOBAL ROGUE DETECT
--

    rogueDetectEnable OBJECT-TYPE
        SYNTAX          INTEGER { disable(0), standard(1), advanced(2),
                                  standard-auto-block(3) }
        MAX-ACCESS      read-write
        STATUS          current
        DESCRIPTION
            "Enable/disable rogue AP detection"
        ::= { rogueDetect 1 }

    rogueDetectSSIDTable OBJECT-TYPE
        SYNTAX          SEQUENCE OF RogueDetectSSIDEntry
        MAX-ACCESS      not-accessible
        STATUS          current
        DESCRIPTION
            "Rogue detect SSID table for the Array"
        ::= { rogueDetect 2 }

    rogueDetectSSIDEntry OBJECT-TYPE
        SYNTAX          RogueDetectSSIDEntry
        MAX-ACCESS      not-accessible
        STATUS          current
        DESCRIPTION
            "Rogue detect SSID table entry"
        INDEX       { rogueDetectSSIDIndex }
        ::= { rogueDetectSSIDTable 1 }

    RogueDetectSSIDEntry ::= SEQUENCE {
        rogueDetectSSIDIndex        Integer32,
        rogueDetectSSIDName         DisplayString,
        rogueDetectSSIDStatus       INTEGER,
        rogueDetectSSIDRowStatus    RowStatus,
        rogueDetectSSIDMatch        INTEGER
    }

    rogueDetectSSIDIndex OBJECT-TYPE
        SYNTAX          Integer32
        MAX-ACCESS      not-accessible
        STATUS          current
        DESCRIPTION
            "Rogue detect SSID table index"
        ::= { rogueDetectSSIDEntry 1 }

    rogueDetectSSIDName OBJECT-TYPE
        SYNTAX          DisplayString(SIZE(1..32))
        MAX-ACCESS      read-create
        STATUS          current
        DESCRIPTION
            "SSID"
        ::= { rogueDetectSSIDEntry 2 }

    rogueDetectSSIDStatus OBJECT-TYPE
        SYNTAX          INTEGER { known(1), approved(2), blocked(3) }
        MAX-ACCESS      read-create
        STATUS          current
        DESCRIPTION
            "SSID status"
        ::= { rogueDetectSSIDEntry 3 }

    rogueDetectSSIDRowStatus OBJECT-TYPE
        SYNTAX          RowStatus
        MAX-ACCESS      read-create
        STATUS          current
        DESCRIPTION
            "Status of the rogue detect SSID table row entry"
        ::= { rogueDetectSSIDEntry 4 }

    rogueDetectSSIDMatch OBJECT-TYPE
        SYNTAX          INTEGER { bssid-or-ssid(0), bssid(1), ssid(2), manufacturer(3) }
        MAX-ACCESS      read-create
        STATUS          current
        DESCRIPTION
            "SSID match"
        ::= { rogueDetectSSIDEntry 5 }

    rogueDetectAPTable OBJECT-TYPE
        SYNTAX          SEQUENCE OF RogueDetectAPEntry
        MAX-ACCESS      not-accessible
        STATUS          current
        DESCRIPTION
            "Table of rogue AP's"
        ::= { rogueDetect 3 }

    rogueDetectAPEntry OBJECT-TYPE
        SYNTAX          RogueDetectAPEntry
        MAX-ACCESS      not-accessible
        STATUS          current
        DESCRIPTION
            "Rogue AP table entry"
        INDEX       { rogueDetectAPIndex }
        ::= { rogueDetectAPTable 1 }

    RogueDetectAPEntry ::= SEQUENCE {
        rogueDetectAPIndex              Integer32,
        rogueDetectAPStatus             INTEGER,
        rogueDetectAPSSID               DisplayString,
        rogueDetectAPBSSID              DisplayString,
        rogueDetectAPManufacturer       DisplayString,
        rogueDetectAPChannel            Integer32,
        rogueDetectAPRSSI               Integer32,
        rogueDetectAPSecurity           DisplayString,
        rogueDetectAPIPAddress          DisplayString,
        rogueDetectAPTimeDiscovered     DisplayString,
        rogueDetectAPTimeLastActive     DisplayString,
        rogueDetectAPType               INTEGER
    }

    rogueDetectAPIndex OBJECT-TYPE
        SYNTAX          Integer32
        MAX-ACCESS      not-accessible
        STATUS          current
        DESCRIPTION
            "Rogue AP index"
        ::= { rogueDetectAPEntry 1 }

    rogueDetectAPStatus OBJECT-TYPE
        SYNTAX          INTEGER { unknown(0), known(1), approved(2), blocked(3) }
        MAX-ACCESS      read-only
        STATUS          current
        DESCRIPTION
            "Rogue AP status"
        ::= { rogueDetectAPEntry 2 }

    rogueDetectAPSSID OBJECT-TYPE
        SYNTAX          DisplayString
        MAX-ACCESS      read-only
        STATUS          current
        DESCRIPTION
            "Rogue AP SSID"
        ::= { rogueDetectAPEntry 3 }

    rogueDetectAPBSSID OBJECT-TYPE
        SYNTAX          DisplayString
        MAX-ACCESS      read-only
        STATUS          current
        DESCRIPTION
            "Rogue AP BSSID"
        ::= { rogueDetectAPEntry 4 }

    rogueDetectAPManufacturer OBJECT-TYPE
        SYNTAX          DisplayString
        MAX-ACCESS      read-only
        STATUS          current
        DESCRIPTION
            "Rogue AP manufacturer"
        ::= { rogueDetectAPEntry 5 }

    rogueDetectAPChannel OBJECT-TYPE
        SYNTAX          Integer32
        MAX-ACCESS      read-only
        STATUS          current
        DESCRIPTION
            "Rogue AP channel"
        ::= { rogueDetectAPEntry 6 }

    rogueDetectAPRSSI OBJECT-TYPE
        SYNTAX          Integer32
        MAX-ACCESS      read-only
        STATUS          current
        DESCRIPTION
            "Rogue AP RSSI"
        ::= { rogueDetectAPEntry 7 }

    rogueDetectAPSecurity OBJECT-TYPE
        SYNTAX          DisplayString
        MAX-ACCESS      read-only
        STATUS          current
        DESCRIPTION
            "Rogue AP security"
        ::= { rogueDetectAPEntry 8 }

    rogueDetectAPIPAddress OBJECT-TYPE
        SYNTAX          DisplayString
        MAX-ACCESS      read-only
        STATUS          current
        DESCRIPTION
            "Rogue AP IP Address"
        ::= { rogueDetectAPEntry 9 }

    rogueDetectAPTimeDiscovered OBJECT-TYPE
        SYNTAX          DisplayString
        MAX-ACCESS      read-only
        STATUS          current
        DESCRIPTION
            "Rogue AP time discovered"
        ::= { rogueDetectAPEntry 10 }

    rogueDetectAPTimeLastActive OBJECT-TYPE
        SYNTAX          DisplayString
        MAX-ACCESS      read-only
        STATUS          current
        DESCRIPTION
            "Rogue AP IP time last active"
        ::= { rogueDetectAPEntry 11 }

    rogueDetectAPType OBJECT-TYPE
        SYNTAX          INTEGER { ibss(1), ess(2) }
        MAX-ACCESS      read-only
        STATUS          current
        DESCRIPTION
            "Rogue AP type"
        ::= { rogueDetectAPEntry 12 }

    rogueDetectSSIDTableReset OBJECT-TYPE
        SYNTAX          INTEGER { reset(1) }
        MAX-ACCESS      read-write
        STATUS          current
        DESCRIPTION
            "Reset rogue detect SSID table (clear all entries)"
        ::= { rogueDetect 4 }

    rogueDetectAPOrigTable OBJECT-TYPE
        SYNTAX          SEQUENCE OF RogueDetectAPOrigTableEntry
        MAX-ACCESS      not-accessible
        STATUS          current
        DESCRIPTION
            "Table of rogue AP's (original)"
        ::= { rogueDetect 5 }

    rogueDetectAPOrigTableEntry OBJECT-TYPE
        SYNTAX          RogueDetectAPOrigTableEntry
        MAX-ACCESS      not-accessible
        STATUS          current
        DESCRIPTION
            "Rogue AP original table entry"
        INDEX       { rogueDetectAPOrigTableIndex }
        ::= { rogueDetectAPOrigTable 1 }

    RogueDetectAPOrigTableEntry ::= SEQUENCE {
        rogueDetectAPOrigTableIndex             Integer32,
        rogueDetectAPOrigTableSSID              DisplayString,
        rogueDetectAPOrigTableBSSID             DisplayString,
        rogueDetectAPOrigTableManufacturer      DisplayString,
        rogueDetectAPOrigTableChannel           Integer32,
        rogueDetectAPOrigTableBand              INTEGER,
        rogueDetectAPOrigTableRSSI              Integer32,
        rogueDetectAPOrigTableSecurity          DisplayString,
        rogueDetectAPOrigTableIPAddress         DisplayString,
        rogueDetectAPOrigTableTimeDiscovered    Counter32,
        rogueDetectAPOrigTableTimeLastActive    Counter32,
        rogueDetectAPOrigTableActive            INTEGER,
        rogueDetectAPOrigTableType              INTEGER
    }

    rogueDetectAPOrigTableIndex OBJECT-TYPE
        SYNTAX          Integer32
        MAX-ACCESS      not-accessible
        STATUS          current
        DESCRIPTION
            "Rogue AP index"
        ::= { rogueDetectAPOrigTableEntry 1 }

    rogueDetectAPOrigTableSSID OBJECT-TYPE
        SYNTAX          DisplayString
        MAX-ACCESS      read-only
        STATUS          current
        DESCRIPTION
            "Rogue AP SSID"
        ::= { rogueDetectAPOrigTableEntry 2 }

    rogueDetectAPOrigTableBSSID OBJECT-TYPE
        SYNTAX          DisplayString
        MAX-ACCESS      read-only
        STATUS          current
        DESCRIPTION
            "Rogue AP BSSID"
        ::= { rogueDetectAPOrigTableEntry 3 }

    rogueDetectAPOrigTableManufacturer OBJECT-TYPE
        SYNTAX          DisplayString
        MAX-ACCESS      read-only
        STATUS          current
        DESCRIPTION
            "Rogue AP manufacturer"
        ::= { rogueDetectAPOrigTableEntry 4 }

    rogueDetectAPOrigTableChannel OBJECT-TYPE
        SYNTAX          Integer32
        MAX-ACCESS      read-only
        STATUS          current
        DESCRIPTION
            "Rogue AP channel"
        ::= { rogueDetectAPOrigTableEntry 5 }

    rogueDetectAPOrigTableBand OBJECT-TYPE
        SYNTAX          INTEGER { dot11a(1), dot11g(2) }
        MAX-ACCESS      read-only
        STATUS          current
        DESCRIPTION
            "Rogue AP 802.11 band"
        ::= { rogueDetectAPOrigTableEntry 6 }

    rogueDetectAPOrigTableRSSI OBJECT-TYPE
        SYNTAX          Integer32
        MAX-ACCESS      read-only
        STATUS          current
        DESCRIPTION
            "Rogue AP RSSI"
        ::= { rogueDetectAPOrigTableEntry 7 }

    rogueDetectAPOrigTableSecurity OBJECT-TYPE
        SYNTAX          DisplayString
        MAX-ACCESS      read-only
        STATUS          current
        DESCRIPTION
            "Rogue AP security"
        ::= { rogueDetectAPOrigTableEntry 8 }

    rogueDetectAPOrigTableIPAddress OBJECT-TYPE
        SYNTAX          DisplayString
        MAX-ACCESS      read-only
        STATUS          current
        DESCRIPTION
            "Rogue AP IP Address"
        ::= { rogueDetectAPOrigTableEntry 9 }

    rogueDetectAPOrigTableTimeDiscovered OBJECT-TYPE
        SYNTAX          Counter32
        MAX-ACCESS      read-only
        STATUS          current
        DESCRIPTION
            "Rogue AP time discovered"
        ::= { rogueDetectAPOrigTableEntry 10 }

    rogueDetectAPOrigTableTimeLastActive OBJECT-TYPE
        SYNTAX          Counter32
        MAX-ACCESS      read-only
        STATUS          current
        DESCRIPTION
            "Rogue AP IP time last active"
        ::= { rogueDetectAPOrigTableEntry 11 }

    rogueDetectAPOrigTableActive OBJECT-TYPE
        SYNTAX          INTEGER { active(1), not-active(2) }
        MAX-ACCESS      read-only
        STATUS          current
        DESCRIPTION
            "Is Rogue AP active?"
        ::= { rogueDetectAPOrigTableEntry 12 }

    rogueDetectAPOrigTableType OBJECT-TYPE
        SYNTAX          INTEGER { ibss(1), ess(2) }
        MAX-ACCESS      read-only
        STATUS          current
        DESCRIPTION
            "Rogue AP type"
        ::= { rogueDetectAPOrigTableEntry 13 }

    rogueDetectAutoBlockEnc OBJECT-TYPE
        SYNTAX          INTEGER { none(0), wep-and-none(1), all(2) }
        MAX-ACCESS      read-write
        STATUS          current
        DESCRIPTION
            "Encryption type for automatic blocking of unknown rogue APs"
        ::= { rogueDetect 6 }

    rogueDetectAutoBlockRSSI OBJECT-TYPE
        SYNTAX          Integer32(-95..-50)
        MAX-ACCESS      read-write
        STATUS          current
        DESCRIPTION
            "Minimum RSSI value for automatic blocking of unknown rogue APs"
        ::= { rogueDetect 7 }

    rogueDetectAutoBlockType OBJECT-TYPE
        SYNTAX          INTEGER { all(0), ibss(1), ess(2) }
        MAX-ACCESS      read-write
        STATUS          current
        DESCRIPTION
            "Type of rogue AP networks to automatically block"
        ::= { rogueDetect 8 }

    rogueDetectAPOrigTablePeriod OBJECT-TYPE
        SYNTAX          Counter32(0..100000000)
        MAX-ACCESS      read-write
        STATUS          current
        DESCRIPTION
            "Specify period for rogue AP table entries (in seconds, 0 - all table entries)"
        ::= { rogueDetect 9 }

    rogueDetectAutoBlockWhitelistTable OBJECT-TYPE
        SYNTAX          SEQUENCE OF RogueDetectAutoBlockWhitelistEntry
        MAX-ACCESS      not-accessible
        STATUS          current
        DESCRIPTION
            "Rogue AP Auto Block channel whitelist"
        ::= { rogueDetect 10 }

    rogueDetectAutoBlockWhitelistEntry OBJECT-TYPE
        SYNTAX          RogueDetectAutoBlockWhitelistEntry
        MAX-ACCESS      not-accessible
        STATUS          current
        DESCRIPTION
            "Rogue AP Auto Block channel whitelist entry"
        INDEX       { rogueDetectAutoBlockWhitelistIndex }
        ::= { rogueDetectAutoBlockWhitelistTable 1 }

    RogueDetectAutoBlockWhitelistEntry ::= SEQUENCE {
        rogueDetectAutoBlockWhitelistIndex         Integer32,
        rogueDetectAutoBlockWhitelistChannel       Integer32,
        rogueDetectAutoBlockWhitelistRowStatus     RowStatus
    }

    rogueDetectAutoBlockWhitelistIndex OBJECT-TYPE
        SYNTAX          Integer32
        MAX-ACCESS      not-accessible
        STATUS          current
        DESCRIPTION
            "Rogue AP Auto Block channel whitelist Index"
        ::= { rogueDetectAutoBlockWhitelistEntry 1 }

    rogueDetectAutoBlockWhitelistChannel OBJECT-TYPE
        SYNTAX          Integer32(1..255)
        MAX-ACCESS      read-create
        STATUS          current
        DESCRIPTION
            "Rogue AP Auto Block channel whitelist channel"
        ::= { rogueDetectAutoBlockWhitelistEntry 2 }

    rogueDetectAutoBlockWhitelistRowStatus OBJECT-TYPE
        SYNTAX          RowStatus
        MAX-ACCESS      read-create
        STATUS          current
        DESCRIPTION
            "Status of the Rogue AP Auto Block channel whitelist row entry"
        ::= { rogueDetectAutoBlockWhitelistEntry 3 }

    rogueDetectAutoBlockWhitelistTableReset OBJECT-TYPE
        SYNTAX          INTEGER { reset(1) }
        MAX-ACCESS      read-write
        STATUS          current
        DESCRIPTION
            "Reset Rogue AP Auto Block channel whitelist"
        ::= { rogueDetect 11 }

--
-- INTERFACE IAP GLOBAL FAST ROAMING
--

    fastRoamingEnable OBJECT-TYPE
        SYNTAX          INTEGER { disable(0), broadcast(1), tunnel(2) }
        MAX-ACCESS      read-write
        STATUS          current
        DESCRIPTION
            "Enable/disable fast roaming"
        ::= { fastRoaming 1 }

    fastRoamingPeerMode OBJECT-TYPE
        SYNTAX          INTEGER { target-only(0), in-range(1), all(2) }
        MAX-ACCESS      read-write
        STATUS          current
        DESCRIPTION
            "Set fast roaming peer mode"
        ::= { fastRoaming 2 }

    fastRoamingTargetArrayTableReset OBJECT-TYPE
        SYNTAX          INTEGER { reset(1) }
        MAX-ACCESS      read-write
        STATUS          current
        DESCRIPTION
            "Reset fast roaming target array table (clear all entries)"
        ::= { fastRoaming 3 }

    fastRoamingLayer OBJECT-TYPE
        SYNTAX          INTEGER { layer-2-only(0), layer-2-and-3(1) }
        MAX-ACCESS      read-write
        STATUS          current
        DESCRIPTION
            "Set fast roaming layer"
        ::= { fastRoaming 5 }

    fastRoamingTargetTable OBJECT-TYPE
        SYNTAX          SEQUENCE OF FastRoamingTargetEntry
        MAX-ACCESS      not-accessible
        STATUS          current
        DESCRIPTION
            "Fast roaming target array table"
        ::= { fastRoaming 6 }

    fastRoamingTargetEntry OBJECT-TYPE
        SYNTAX          FastRoamingTargetEntry
        MAX-ACCESS      not-accessible
        STATUS          current
        DESCRIPTION
            "Fast roaming target array table entry"
        INDEX       { fastRoamingTargetIndex }
        ::= { fastRoamingTargetTable 1 }

    FastRoamingTargetEntry ::= SEQUENCE {
        fastRoamingTargetIndex              Integer32,
        fastRoamingTargetType               INTEGER,
        fastRoamingTargetMacAddress         DisplayString,
        fastRoamingTargetIpAddress          IpAddress,
        fastRoamingTargetHostname           DisplayString,
        fastRoamingTargetRowStatus          RowStatus
    }

    fastRoamingTargetIndex OBJECT-TYPE
        SYNTAX          Integer32
        MAX-ACCESS      not-accessible
        STATUS          current
        DESCRIPTION
            "Fast roaming target array table index"
        ::= { fastRoamingTargetEntry 1 }

    fastRoamingTargetType OBJECT-TYPE
        SYNTAX          INTEGER { mac(0), ip(1), hostname(2) }
        MAX-ACCESS      read-create
        STATUS          current
        DESCRIPTION
            "Type of the fast roaming target array table row entry"
        ::= { fastRoamingTargetEntry 2 }

    fastRoamingTargetMacAddress OBJECT-TYPE
        SYNTAX          DisplayString(SIZE(12..17))
        MAX-ACCESS      read-create
        STATUS          current
        DESCRIPTION
            "Base IAP MAC address of the target array"
        ::= { fastRoamingTargetEntry 3 }

    fastRoamingTargetIpAddress OBJECT-TYPE
        SYNTAX          IpAddress
        MAX-ACCESS      read-create
        STATUS          current
        DESCRIPTION
            "IP address of the target array"
        ::= { fastRoamingTargetEntry 4 }

    fastRoamingTargetHostname OBJECT-TYPE
        SYNTAX          DisplayString(SIZE(1.. 255))
        MAX-ACCESS      read-create
        STATUS          current
        DESCRIPTION
            "Hostname of the target array"
        ::= { fastRoamingTargetEntry 5 }

    fastRoamingTargetRowStatus OBJECT-TYPE
        SYNTAX          RowStatus
        MAX-ACCESS      read-create
        STATUS          current
        DESCRIPTION
            "Status of the fast roaming target array table row entry"
        ::= { fastRoamingTargetEntry 6 }

--
-- INTERFACE IAP GLOBAL AUTO CELL
--

    autoCellEnable OBJECT-TYPE
        SYNTAX          INTEGER { enable(1) }
        MAX-ACCESS      read-write
        STATUS          current
        DESCRIPTION
            "Enable auto cell size configuration"
        ::= { autoCell 1 }

    autoCellOverlap OBJECT-TYPE
        SYNTAX          Integer32(0..100)
        MAX-ACCESS      read-write
        STATUS          current
        DESCRIPTION
            "Set auto cell size overlap (in percents)"
        ::= { autoCell 2 }

    autoCellPeriod OBJECT-TYPE
        SYNTAX          Integer32(0..3000000)
        MAX-ACCESS      read-write
        STATUS          current
        DESCRIPTION
            "Set period to run auto cell size assignment (in seconds from 60 to 3000000, 0 - none)"
        ::= { autoCell 3 }

    autoCellMinTxPwr OBJECT-TYPE
        SYNTAX          Integer32(-15..20)
        MAX-ACCESS      read-write
        STATUS          current
        DESCRIPTION
            "Set auto cell size minimum Tx power"
        ::= { autoCell 4 }

    autoCellByChan OBJECT-TYPE
        SYNTAX          INTEGER { enable(1) }
        MAX-ACCESS      read-write
        STATUS          current
        DESCRIPTION
            "Enable auto cell by channel configuration"
        ::= { autoCell 5 }


--
-- INTERFACE IAP GLOBAL IDS
--

    idsEventTable OBJECT-TYPE
        SYNTAX          SEQUENCE OF IdsEventEntry
        MAX-ACCESS      not-accessible
        STATUS          current
        DESCRIPTION
            "IDS event table"
        ::= { ids 1 }

    idsEventEntry OBJECT-TYPE
        SYNTAX          IdsEventEntry
        MAX-ACCESS      not-accessible
        STATUS          current
        DESCRIPTION
            "IDS event table entry"
        INDEX       { idsEventIndex }
        ::= { idsEventTable 1 }

    IdsEventEntry ::= SEQUENCE {
        idsEventIndex           Integer32,
        idsEventId              INTEGER,
        idsEventTime            DisplayString,
        idsEventTimestamp       Counter32,
        idsEventIAP             DisplayString,
        idsEventChannel         Integer32,
        idsEventPeriod          Counter32,
        idsEventCurPackets      Counter32,
        idsEventAvgPackets      Counter32,
        idsEventMaxPackets      Counter32,
        idsEventMacAddress      DisplayString,
        idsEventSSID            DisplayString
    }

    idsEventIndex OBJECT-TYPE
        SYNTAX          Integer32
        MAX-ACCESS      not-accessible
        STATUS          current
        DESCRIPTION
            "IDS event index"
        ::= { idsEventEntry 1 }

    idsEventId OBJECT-TYPE
        SYNTAX          INTEGER { beacon-flood(1), probe-req-flood(2), auth-flood(3),
                                  assoc-flood(4), disassoc-flood(5), deauth-flood(6),
                                  eap-flood(7), ap-impersonation(8), disassoc-attack(9),
                                  deauth-attack(10), duration-attack(11), mic-error-attack(12),
                                  null-probe-resp(13), seq-num-anomaly(14), sta-impersonation(15),
                                  sta-broadcast(16), evil-twin-attack(17), rf-jamming(18) }
        MAX-ACCESS      read-only
        STATUS          current
        DESCRIPTION
            "IDS event detected"
        ::= { idsEventEntry 2 }

    idsEventTime OBJECT-TYPE
        SYNTAX          DisplayString
        MAX-ACCESS      read-only
        STATUS          current
        DESCRIPTION
            "IDS event detection time"
        ::= { idsEventEntry 3 }

    idsEventTimestamp OBJECT-TYPE
        SYNTAX          Counter32
        MAX-ACCESS      read-only
        STATUS          current
        DESCRIPTION
            "IDS event detection time (in seconds)"
        ::= { idsEventEntry 4 }

    idsEventIAP OBJECT-TYPE
        SYNTAX          DisplayString
        MAX-ACCESS      read-only
        STATUS          current
        DESCRIPTION
            "IAP IDS event was detected on"
        ::= { idsEventEntry 5 }

    idsEventChannel OBJECT-TYPE
        SYNTAX          Integer32
        MAX-ACCESS      read-only
        STATUS          current
        DESCRIPTION
            "Channel IDS event was detected on"
        ::= { idsEventEntry 6 }

    idsEventPeriod OBJECT-TYPE
        SYNTAX          Counter32
        MAX-ACCESS      read-only
        STATUS          current
        DESCRIPTION
            "IDS event detection time period (in seconds)"
        ::= { idsEventEntry 7 }

    idsEventCurPackets OBJECT-TYPE
        SYNTAX          Counter32
        MAX-ACCESS      read-only
        STATUS          current
        DESCRIPTION
            "IDS event current number of packets received"
        ::= { idsEventEntry 8 }

    idsEventAvgPackets OBJECT-TYPE
        SYNTAX          Counter32
        MAX-ACCESS      read-only
        STATUS          current
        DESCRIPTION
            "IDS event average number of packets received"
        ::= { idsEventEntry 9 }

    idsEventMaxPackets OBJECT-TYPE
        SYNTAX          Counter32
        MAX-ACCESS      read-only
        STATUS          current
        DESCRIPTION
            "IDS event maximum number of packets received"
        ::= { idsEventEntry 10 }

    idsEventMacAddress OBJECT-TYPE
        SYNTAX          DisplayString
        MAX-ACCESS      read-only
        STATUS          current
        DESCRIPTION
            "IDS event MAC address"
        ::= { idsEventEntry 11 }

    idsEventSSID OBJECT-TYPE
        SYNTAX          DisplayString
        MAX-ACCESS      read-only
        STATUS          current
        DESCRIPTION
            "IDS event SSID"
        ::= { idsEventEntry 12 }

    idsDosAttack        OBJECT IDENTIFIER ::= { ids 2 }
    idsImpersonation    OBJECT IDENTIFIER ::= { ids 3 }

--
-- INTERFACE IAP GLOBAL IDS DOS ATTACK
--

    idsBeaconFloodMode OBJECT-TYPE
        SYNTAX          INTEGER { disable(0), manual(1), auto(2) }
        MAX-ACCESS      read-write
        STATUS          current
        DESCRIPTION
            "Beacon flood detection mode"
        ::= { idsDosAttack 1 }

    idsBeaconFloodThreshold OBJECT-TYPE
        SYNTAX          Integer32(1..100000000)
        MAX-ACCESS      read-write
        STATUS          current
        DESCRIPTION
            "Number of packets received in a period of time to trigger beacon flood detection"
        ::= { idsDosAttack 2 }

    idsBeaconFloodPeriod OBJECT-TYPE
        SYNTAX          Integer32(10..3600)
        MAX-ACCESS      read-write
        STATUS          current
        DESCRIPTION
            "Time period for beacon flood detection (in seconds, must be an increment of 10)"
        ::= { idsDosAttack 3 }

    idsProbeReqFloodMode OBJECT-TYPE
        SYNTAX          INTEGER { disable(0), manual(1), auto(2) }
        MAX-ACCESS      read-write
        STATUS          current
        DESCRIPTION
            "Probe request flood detection mode"
        ::= { idsDosAttack 4 }

    idsProbeReqFloodThreshold OBJECT-TYPE
        SYNTAX          Integer32(1..100000000)
        MAX-ACCESS      read-write
        STATUS          current
        DESCRIPTION
            "Number of packets received in a period of time to trigger probe request flood detection"
        ::= { idsDosAttack 5 }

    idsProbeReqFloodPeriod OBJECT-TYPE
        SYNTAX          Integer32(10..3600)
        MAX-ACCESS      read-write
        STATUS          current
        DESCRIPTION
            "Time period for probe request flood detection (in seconds, must be an increment of 10)"
        ::= { idsDosAttack 6 }

    idsAuthFloodMode OBJECT-TYPE
        SYNTAX          INTEGER { disable(0), manual(1), auto(2) }
        MAX-ACCESS      read-write
        STATUS          current
        DESCRIPTION
            "Authentication flood detection mode"
        ::= { idsDosAttack 7 }

    idsAuthFloodThreshold OBJECT-TYPE
        SYNTAX          Integer32(1..100000000)
        MAX-ACCESS      read-write
        STATUS          current
        DESCRIPTION
            "Number of packets received in a period of time to trigger authentication flood detection"
        ::= { idsDosAttack 8 }

    idsAuthFloodPeriod OBJECT-TYPE
        SYNTAX          Integer32(10..3600)
        MAX-ACCESS      read-write
        STATUS          current
        DESCRIPTION
            "Time period for authentication flood detection (in seconds, must be an increment of 10)"
        ::= { idsDosAttack 9 }

    idsAssocFloodMode OBJECT-TYPE
        SYNTAX          INTEGER { disable(0), manual(1), auto(2) }
        MAX-ACCESS      read-write
        STATUS          current
        DESCRIPTION
            "Association flood detection mode"
        ::= { idsDosAttack 10 }

    idsAssocFloodThreshold OBJECT-TYPE
        SYNTAX          Integer32(1..100000000)
        MAX-ACCESS      read-write
        STATUS          current
        DESCRIPTION
            "Number of packets received in a period of time to trigger association flood detection"
        ::= { idsDosAttack 11 }

    idsAssocFloodPeriod OBJECT-TYPE
        SYNTAX          Integer32(10..3600)
        MAX-ACCESS      read-write
        STATUS          current
        DESCRIPTION
            "Time period for association flood detection (in seconds, must be an increment of 10)"
        ::= { idsDosAttack 12 }

    idsDisassocFloodMode OBJECT-TYPE
        SYNTAX          INTEGER { disable(0), manual(1), auto(2) }
        MAX-ACCESS      read-write
        STATUS          current
        DESCRIPTION
            "Disassociation flood detection mode"
        ::= { idsDosAttack 13 }

    idsDisassocFloodThreshold OBJECT-TYPE
        SYNTAX          Integer32(1..100000000)
        MAX-ACCESS      read-write
        STATUS          current
        DESCRIPTION
            "Number of packets received in a period of time to trigger disassociation flood detection"
        ::= { idsDosAttack 14 }

    idsDisassocFloodPeriod OBJECT-TYPE
        SYNTAX          Integer32(10..3600)
        MAX-ACCESS      read-write
        STATUS          current
        DESCRIPTION
            "Time period for disassociation flood detection (in seconds, must be an increment of 10)"
        ::= { idsDosAttack 15 }

    idsDeauthFloodMode OBJECT-TYPE
        SYNTAX          INTEGER { disable(0), manual(1), auto(2) }
        MAX-ACCESS      read-write
        STATUS          current
        DESCRIPTION
            "Deauthentication flood detection mode"
        ::= { idsDosAttack 16 }

    idsDeauthFloodThreshold OBJECT-TYPE
        SYNTAX          Integer32(1..100000000)
        MAX-ACCESS      read-write
        STATUS          current
        DESCRIPTION
            "Number of packets received in a period of time to trigger deauthentication flood detection"
        ::= { idsDosAttack 17 }

    idsDeauthFloodPeriod OBJECT-TYPE
        SYNTAX          Integer32(10..3600)
        MAX-ACCESS      read-write
        STATUS          current
        DESCRIPTION
            "Time period for deauthentication flood detection (in seconds, must be an increment of 10)"
        ::= { idsDosAttack 18 }

    idsEAPFloodMode OBJECT-TYPE
        SYNTAX          INTEGER { disable(0), manual(1), auto(2) }
        MAX-ACCESS      read-write
        STATUS          current
        DESCRIPTION
            "EAP flood detection mode"
        ::= { idsDosAttack 19 }

    idsEAPFloodThreshold OBJECT-TYPE
        SYNTAX          Integer32(1..100000000)
        MAX-ACCESS      read-write
        STATUS          current
        DESCRIPTION
            "Number of packets received in a period of time to trigger EAP flood detection"
        ::= { idsDosAttack 20 }

    idsEAPFloodPeriod OBJECT-TYPE
        SYNTAX          Integer32(10..3600)
        MAX-ACCESS      read-write
        STATUS          current
        DESCRIPTION
            "Time period for EAP flood detection (in seconds, must be an increment of 10)"
        ::= { idsDosAttack 21 }

    idsNullProbeRespEnable OBJECT-TYPE
        SYNTAX          INTEGER { disable(0), enable(1) }
        MAX-ACCESS      read-write
        STATUS          current
        DESCRIPTION
            "Enable/disable null probe response detection"
        ::= { idsDosAttack 22 }

    idsNullProbeRespThreshold OBJECT-TYPE
        SYNTAX          Integer32(1..100000000)
        MAX-ACCESS      read-write
        STATUS          current
        DESCRIPTION
            "Number of packets received in a period of time to trigger null probe response detection"
        ::= { idsDosAttack 23 }

    idsNullProbeRespPeriod OBJECT-TYPE
        SYNTAX          Integer32(10..3600)
        MAX-ACCESS      read-write
        STATUS          current
        DESCRIPTION
            "Time period for null probe response detection (in seconds, must be an increment of 10)"
        ::= { idsDosAttack 24 }

    idsMICErrorAttackEnable OBJECT-TYPE
        SYNTAX          INTEGER { disable(0), enable(1) }
        MAX-ACCESS      read-write
        STATUS          current
        DESCRIPTION
            "Enable/disable MIC error attack detection"
        ::= { idsDosAttack 25 }

    idsMICErrorAttackThreshold OBJECT-TYPE
        SYNTAX          Integer32(1..100000000)
        MAX-ACCESS      read-write
        STATUS          current
        DESCRIPTION
            "Number of errors captured in a period of time to trigger MIC error attack detection"
        ::= { idsDosAttack 26 }

    idsMICErrorAttackPeriod OBJECT-TYPE
        SYNTAX          Integer32(10..3600)
        MAX-ACCESS      read-write
        STATUS          current
        DESCRIPTION
            "Time period for MIC error attack detection (in seconds, must be an increment of 10)"
        ::= { idsDosAttack 27 }

    idsDisassocAttackEnable OBJECT-TYPE
        SYNTAX          INTEGER { disable(0), enable(1) }
        MAX-ACCESS      read-write
        STATUS          current
        DESCRIPTION
            "Enable/disable disassociation attack detection"
        ::= { idsDosAttack 28 }

    idsDisassocAttackThreshold OBJECT-TYPE
        SYNTAX          Integer32(1..100000000)
        MAX-ACCESS      read-write
        STATUS          current
        DESCRIPTION
            "Number of spoofed packets captured in a period of time to trigger disassociation attack detection"
        ::= { idsDosAttack 29 }

    idsDisassocAttackPeriod OBJECT-TYPE
        SYNTAX          Integer32(10..3600)
        MAX-ACCESS      read-write
        STATUS          current
        DESCRIPTION
            "Time period for disassociation attack detection (in seconds, must be an increment of 10)"
        ::= { idsDosAttack 30 }

    idsDeauthAttackEnable OBJECT-TYPE
        SYNTAX          INTEGER { disable(0), enable(1) }
        MAX-ACCESS      read-write
        STATUS          current
        DESCRIPTION
            "Enable/disable deauthentication attack detection"
        ::= { idsDosAttack 31 }

    idsDeauthAttackThreshold OBJECT-TYPE
        SYNTAX          Integer32(1..100000000)
        MAX-ACCESS      read-write
        STATUS          current
        DESCRIPTION
            "Number of spoofed packets captured in a period of time to trigger deauthentication attack detection"
        ::= { idsDosAttack 32 }

    idsDeauthAttackPeriod OBJECT-TYPE
        SYNTAX          Integer32(10..3600)
        MAX-ACCESS      read-write
        STATUS          current
        DESCRIPTION
            "Time period for deauthentication attack detection (in seconds, must be an increment of 10)"
        ::= { idsDosAttack 33 }

    idsDurationAttackEnable OBJECT-TYPE
        SYNTAX          INTEGER { disable(0), enable(1) }
        MAX-ACCESS      read-write
        STATUS          current
        DESCRIPTION
            "Enable/disable duration attack detection"
        ::= { idsDosAttack 34 }

    idsDurationAttackThreshold OBJECT-TYPE
        SYNTAX          Integer32(1..100000000)
        MAX-ACCESS      read-write
        STATUS          current
        DESCRIPTION
            "Number of bad NAV occurrences in a period of time to trigger duration attack detection"
        ::= { idsDosAttack 35 }

    idsDurationAttackPeriod OBJECT-TYPE
        SYNTAX          Integer32(1..3600)
        MAX-ACCESS      read-write
        STATUS          current
        DESCRIPTION
            "Time period for duration attack detection (in seconds)"
        ::= { idsDosAttack 36 }

    idsDurationAttackNAV OBJECT-TYPE
        SYNTAX          Integer32(1..32767)
        MAX-ACCESS      read-write
        STATUS          current
        DESCRIPTION
            "NAV value to trigger duration attack detection"
        ::= { idsDosAttack 37 }

--
-- INTERFACE IAP GLOBAL IDS IMPERSONATION
--

    idsAPImpersonationEnable OBJECT-TYPE
        SYNTAX          INTEGER { disable(0), enable(1) }
        MAX-ACCESS      read-write
        STATUS          current
        DESCRIPTION
            "Enable/disable AP impersonation detection"
        ::= { idsImpersonation 1 }

    idsAPImpersonationThreshold OBJECT-TYPE
        SYNTAX          Integer32(1..100000000)
        MAX-ACCESS      read-write
        STATUS          current
        DESCRIPTION
            "Number of spoofed packets captured in a period of time to trigger AP impersonation detection"
        ::= { idsImpersonation 2 }

    idsAPImpersonationPeriod OBJECT-TYPE
        SYNTAX          Integer32(10..3600)
        MAX-ACCESS      read-write
        STATUS          current
        DESCRIPTION
            "Time period for AP impersonation detection (in seconds, must be an increment of 10)"
        ::= { idsImpersonation 3 }

    idsStationImpersonationEnable OBJECT-TYPE
        SYNTAX          INTEGER { disable(0), enable(1) }
        MAX-ACCESS      read-write
        STATUS          current
        DESCRIPTION
            "Enable/disable station impersonation detection"
        ::= { idsImpersonation 4 }

    idsStationImpersonationThreshold OBJECT-TYPE
        SYNTAX          Integer32(1..100000000)
        MAX-ACCESS      read-write
        STATUS          current
        DESCRIPTION
            "Number of events detected in a period of time to trigger station impersonation detection"
        ::= { idsImpersonation 5 }

    idsStationImpersonationPeriod OBJECT-TYPE
        SYNTAX          Integer32(1..3600)
        MAX-ACCESS      read-write
        STATUS          current
        DESCRIPTION
            "Time period for station impersonation detection (in seconds)"
        ::= { idsImpersonation 6 }

    idsSeqNumAnomalyMode OBJECT-TYPE
        SYNTAX          INTEGER { disable(0), mgmt(1), data(2) }
        MAX-ACCESS      read-write
        STATUS          current
        DESCRIPTION
            "Packet sequence number anomaly detection mode"
        ::= { idsImpersonation 7 }

    idsEvilTwinAttackEnable OBJECT-TYPE
        SYNTAX          INTEGER { disable(0), enable(1) }
        MAX-ACCESS      read-write
        STATUS          current
        DESCRIPTION
            "Enable/disable evil twin attack detection"
        ::= { idsImpersonation 8 }

    idsSeqNumAnomalyGap OBJECT-TYPE
        SYNTAX          Integer32(5..1000)
        MAX-ACCESS      read-write
        STATUS          current
        DESCRIPTION
            "Sequence number gap considered as a normal sequence number change"
        ::= { idsImpersonation 9 }

    idsEventTablePeriod OBJECT-TYPE
        SYNTAX          Counter32(0..100000000)
        MAX-ACCESS      read-write
        STATUS          current
        DESCRIPTION
            "Specify period for IDS event table entries (in seconds, 0 - all table entries)"
        ::= { ids 4 }

--
-- INTERFACE IAP GLOBAL RF MONITOR
--

    rfMonitorMode OBJECT-TYPE
        SYNTAX          INTEGER { disable(0), dedicated(1), timeshare(2) }
        MAX-ACCESS      read-write
        STATUS          current
        DESCRIPTION
            "Set RF monitor mode"
        ::= { rfMonitor 1 }

    rfMonitorTimeshareScanInterval OBJECT-TYPE
        SYNTAX          Integer32(6..600)
        MAX-ACCESS      read-write
        STATUS          current
        DESCRIPTION
            "Set RF monitor timeshare scanning interval (seconds between off channel scans)"
        ::= { rfMonitor 2 }

    rfMonitorTimeshareStationThreshold OBJECT-TYPE
        SYNTAX          Integer32(0..240)
        MAX-ACCESS      read-write
        STATUS          current
        DESCRIPTION
            "Set RF monitor timeshare station threshold (station count above which scanning stops)"
        ::= { rfMonitor 3 }

    rfMonitorTimeshareTrafficThreshold OBJECT-TYPE
        SYNTAX          Integer32(0..50000)
        MAX-ACCESS      read-write
        STATUS          current
        DESCRIPTION
            "Set RF monitor timeshare traffic threshold (packets/second above which scanning stops)"
        ::= { rfMonitor 4 }

--
-- INTERFACE IAP GLOBAL 11A
--

    global11aIAPEnable OBJECT-TYPE
        SYNTAX          INTEGER { all-down(0), all-up(1) }
        MAX-ACCESS      read-write
        STATUS          current
        DESCRIPTION
            "Bring all IAPs up or down"
        ::= { global11a 1 }

    global11aIAPCellSize OBJECT-TYPE
        SYNTAX          INTEGER { none(0), small(1), medium(2), large(3),
                                  max(4), auto(5), monitor(6) }
        MAX-ACCESS      read-write
        STATUS          current
        DESCRIPTION
            "Set up RF cell size base on Tx pwr and Rx Threshold"
        ::= { global11a 2 }

    global11aIAPTxPwr OBJECT-TYPE
        SYNTAX          Integer32(-15..20)
        MAX-ACCESS      read-write
        STATUS          current
        DESCRIPTION
            "Maximum Tx power output from any radio"
        ::= { global11a 3 }

    global11aIAPRxThreshold OBJECT-TYPE
        SYNTAX          Integer32(-100..0)
        MAX-ACCESS      read-write
        STATUS          current
        DESCRIPTION
            "Rx (deferred) threshold setting"
        ::= { global11a 4 }

    global11aIAPAutoChannelEnable OBJECT-TYPE
        SYNTAX          INTEGER { enable(1), negotiate(2) }
        MAX-ACCESS      read-write
        STATUS          current
        DESCRIPTION
            "Set to 1 to enable auto channel configuration, 2 to negotiate airtime with other arrays before enabling auto channel configuration"
        ::= { global11a 5 }

    global11aIAPFragThreshold OBJECT-TYPE
        SYNTAX          Integer32(256..2346)
        MAX-ACCESS      read-write
        STATUS          current
        DESCRIPTION
            "Fragmentation threshold"
        ::= { global11a 6 }

    global11aIAPRTSThreshold OBJECT-TYPE
        SYNTAX          Integer32(1..2347)
        MAX-ACCESS      read-write
        STATUS          current
        DESCRIPTION
            "RTS threshold"
        ::= { global11a 7 }

    rates11a        OBJECT IDENTIFIER ::= { global11a 8 }

    global11aIAPAutoCellEnable OBJECT-TYPE
        SYNTAX          INTEGER { enable(1) }
        MAX-ACCESS      read-write
        STATUS          current
        DESCRIPTION
            "Enable auto cell size configuration"
        ::= { global11a 9 }

    autoChannelList11a      OBJECT IDENTIFIER ::= { global11a 10 }

    global11aIAPChannelReset OBJECT-TYPE
        SYNTAX          INTEGER { reset(1) }
        MAX-ACCESS      read-write
        STATUS          current
        DESCRIPTION
            "Reset all 5GHz channels back to factory defaults"
        ::= { global11a 11 }

    global11aIAPAutoCellOverlap OBJECT-TYPE
        SYNTAX          Integer32(0..100)
        MAX-ACCESS      read-write
        STATUS          current
        DESCRIPTION
            "Set auto cell size overlap (in percents)"
        ::= { global11a 12 }

    global11aIAPAutoCellPeriod OBJECT-TYPE
        SYNTAX          Integer32(0..3000000)
        MAX-ACCESS      read-write
        STATUS          current
        DESCRIPTION
            "Set period to run auto cell size assignment (in seconds from 60 to 3000000, 0 - none)"
        ::= { global11a 13 }

    global11aIAPAutoCellMinTxPwr OBJECT-TYPE
        SYNTAX          Integer32(-15..20)
        MAX-ACCESS      read-write
        STATUS          current
        DESCRIPTION
            "Set auto cell size minimum Tx power"
        ::= { global11a 14 }

    global11aIAPMaxStations OBJECT-TYPE
        SYNTAX          Integer32(1..3840)
        MAX-ACCESS      read-write
        STATUS          current
        DESCRIPTION
            "Maximum number of associated stations per array"
        ::= { global11a 15 }

    global11aIAPMaxIapStations OBJECT-TYPE
        SYNTAX          Integer32(1..240)
        MAX-ACCESS      read-write
        STATUS          current
        DESCRIPTION
            "Maximum number of associated stations per IAP"
        ::= { global11a 16 }

    global11aIAPAutoCellByChan OBJECT-TYPE
        SYNTAX          INTEGER { enable(1) }
        MAX-ACCESS      read-write
        STATUS          current
        DESCRIPTION
            "Enable auto cell by channel"
        ::= { global11a 17 }


--
-- INTERFACE IAP GLOBAL 11A RATES
--

    rates11aSet OBJECT-TYPE
        SYNTAX          INTEGER { default(1), optimize-range(2),
                                  optimize-throughput(3) }
        MAX-ACCESS      read-write
        STATUS          current
        DESCRIPTION
            "Set rates to a pre-defined set"
        ::= { rates11a 1 }

    rates11aTable OBJECT-TYPE
        SYNTAX          SEQUENCE OF Rates11aEntry
        MAX-ACCESS      not-accessible
        STATUS          current
        DESCRIPTION
            "802.11a Rates for the Array"
        ::= { rates11a 2 }

    rates11aEntry OBJECT-TYPE
        SYNTAX          Rates11aEntry
        MAX-ACCESS      not-accessible
        STATUS          current
        DESCRIPTION
            "Rates table entry"
        INDEX       { rates11aIndex }
        ::= { rates11aTable 1 }

    Rates11aEntry ::= SEQUENCE {
        rates11aIndex       Integer32,
        rates11aRate        DisplayString,
        rates11aStatus      INTEGER
    }

    rates11aIndex OBJECT-TYPE
        SYNTAX          Integer32
        MAX-ACCESS      not-accessible
        STATUS          current
        DESCRIPTION
            "Rates table index"
        ::= { rates11aEntry 1 }

    rates11aRate OBJECT-TYPE
        SYNTAX          DisplayString
        MAX-ACCESS      read-only
        STATUS          current
        DESCRIPTION
            "802.11a rate"
        ::= { rates11aEntry 2 }

    rates11aStatus OBJECT-TYPE
        SYNTAX          INTEGER { disabled(0), basic(1), supported(2) }
        MAX-ACCESS      read-write
        STATUS          current
        DESCRIPTION
            "802.11a rate status"
        ::= { rates11aEntry 3 }

--
-- INTERFACE IAP GLOBAL 11A AUTO CHANNEL LIST
--

    autoChannelList11aSet OBJECT-TYPE
        SYNTAX          INTEGER { default(1), use-all(2) }
        MAX-ACCESS      read-write
        STATUS          current
        DESCRIPTION
            "Set channel list to defaults or all available channels"
        ::= { autoChannelList11a 1 }

    autoChannelList11aTable OBJECT-TYPE
        SYNTAX          SEQUENCE OF AutoChannelList11aEntry
        MAX-ACCESS      not-accessible
        STATUS          current
        DESCRIPTION
            "802.11a auto channel list"
        ::= { autoChannelList11a 2 }

    autoChannelList11aEntry OBJECT-TYPE
        SYNTAX          AutoChannelList11aEntry
        MAX-ACCESS      not-accessible
        STATUS          current
        DESCRIPTION
            "Auto channel list entry"
        INDEX       { autoChannelList11aIndex }
        ::= { autoChannelList11aTable 1 }

    AutoChannelList11aEntry ::= SEQUENCE {
        autoChannelList11aIndex         Integer32,
        autoChannelList11aChannel       Integer32,
        autoChannelList11aStatus        INTEGER
    }

    autoChannelList11aIndex OBJECT-TYPE
        SYNTAX          Integer32
        MAX-ACCESS      not-accessible
        STATUS          current
        DESCRIPTION
            "Auto channel list index"
        ::= { autoChannelList11aEntry 1 }

    autoChannelList11aChannel OBJECT-TYPE
        SYNTAX          Integer32
        MAX-ACCESS      read-only
        STATUS          current
        DESCRIPTION
            "Channel number"
        ::= { autoChannelList11aEntry 2 }

    autoChannelList11aStatus OBJECT-TYPE
        SYNTAX          INTEGER { disabled(0), enabled(1) }
        MAX-ACCESS      read-write
        STATUS          current
        DESCRIPTION
            "Channel status"
        ::= { autoChannelList11aEntry 3 }

--
-- INTERFACE IAP GLOBAL 11BG
--

    global11bgIAPEnable OBJECT-TYPE
        SYNTAX          INTEGER { all-down(0), all-up(1) }
        MAX-ACCESS      read-write
        STATUS          current
        DESCRIPTION
            "Bring all IAPs up or down"
        ::= { global11bg 1 }

    global11bgIAPCellSize OBJECT-TYPE
        SYNTAX          INTEGER { none(0), small(1), medium(2), large(3),
                                  max(4), auto(5), monitor(6) }
        MAX-ACCESS      read-write
        STATUS          current
        DESCRIPTION
            "Set up RF cell size base on Tx pwr and Rx Threshold"
        ::= { global11bg 2 }

    global11bgIAPTxPwr OBJECT-TYPE
        SYNTAX          Integer32(-15..20)
        MAX-ACCESS      read-write
        STATUS          current
        DESCRIPTION
            "Maximum Tx power output from any radio"
        ::= { global11bg 3 }

    global11bgIAPRxThreshold OBJECT-TYPE
        SYNTAX          Integer32(-100..0)
        MAX-ACCESS      read-write
        STATUS          current
        DESCRIPTION
            "Rx (deferred) threshold setting"
        ::= { global11bg 4 }

    global11bgIAPAutoChannelEnable OBJECT-TYPE
        SYNTAX          INTEGER { enable(1), negotiate(2) }
        MAX-ACCESS      read-write
        STATUS          current
        DESCRIPTION
            "Set to 1 to enable auto channel configuration, 2 to negotiate airtime with other arrays before enabling auto channel configuration"
        ::= { global11bg 5 }

    global11bgIAPFragThreshold OBJECT-TYPE
        SYNTAX          Integer32(256..2346)
        MAX-ACCESS      read-write
        STATUS          current
        DESCRIPTION
            "Fragmentation threshold"
        ::= { global11bg 6 }

    global11bgIAPRTSThreshold OBJECT-TYPE
        SYNTAX          Integer32(1..2347)
        MAX-ACCESS      read-write
        STATUS          current
        DESCRIPTION
            "RTS threshold"
        ::= { global11bg 7 }

    global11bgIAPgOnly OBJECT-TYPE
        SYNTAX          INTEGER { disable(0), enable(1) }
        MAX-ACCESS      read-write
        STATUS          current
        DESCRIPTION
            "Enable/disable 802.11g only mode"
        ::= { global11bg 8 }

    global11bgIAPgProtect OBJECT-TYPE
        SYNTAX          INTEGER { disable(0), auto-cts(1), auto-rts(2) }
        MAX-ACCESS      read-write
        STATUS          current
        DESCRIPTION
            "Enable/disable automatic 802.11g protection"
        ::= { global11bg 9 }

    global11bgIAPPreamble OBJECT-TYPE
        SYNTAX          INTEGER { long-only(0), auto-length(1) }
        MAX-ACCESS      read-write
        STATUS          current
        DESCRIPTION
            "Set preamble"
        ::= { global11bg 10 }

    global11bgIAPSlotTime OBJECT-TYPE
        SYNTAX          INTEGER { auto-time(0), short-only(1) }
        MAX-ACCESS      read-write
        STATUS          current
        DESCRIPTION
            "Set slot time"
        ::= { global11bg 11 }

    rates11bg        OBJECT IDENTIFIER ::= { global11bg 12 }

    global11bgIAPAutoCellEnable OBJECT-TYPE
        SYNTAX          INTEGER { enable(1) }
        MAX-ACCESS      read-write
        STATUS          current
        DESCRIPTION
            "Enable auto cell size configuration"
        ::= { global11bg 13 }

    autoChannelList11bg     OBJECT IDENTIFIER ::= { global11bg 14 }

    global11bgIAPChannelReset OBJECT-TYPE
        SYNTAX          INTEGER { reset(1) }
        MAX-ACCESS      read-write
        STATUS          current
        DESCRIPTION
            "Reset all 2.4GHz channels back to factory defaults"
        ::= { global11bg 15 }

    global11bgIAPAutoCellOverlap OBJECT-TYPE
        SYNTAX          Integer32(0..100)
        MAX-ACCESS      read-write
        STATUS          current
        DESCRIPTION
            "Set auto cell size overlap (in percents)"
        ::= { global11bg 16 }

    global11bgIAPAutoCellPeriod OBJECT-TYPE
        SYNTAX          Integer32(0..3000000)
        MAX-ACCESS      read-write
        STATUS          current
        DESCRIPTION
            "Set period to run auto cell size assignment (in seconds from 60 to 3000000, 0 - none)"
        ::= { global11bg 17 }

    global11bgIAPAutoCellMinTxPwr OBJECT-TYPE
        SYNTAX          Integer32(-15..20)
        MAX-ACCESS      read-write
        STATUS          current
        DESCRIPTION
            "Set auto cell size minimum Tx power"
        ::= { global11bg 18 }

    global11bgIAPMaxStations OBJECT-TYPE
        SYNTAX          Integer32(1..3840)
        MAX-ACCESS      read-write
        STATUS          current
        DESCRIPTION
            "Maximum number of associated stations per array"
        ::= { global11bg 19 }

    global11bgIAPMaxIapStations OBJECT-TYPE
        SYNTAX          Integer32(1..240)
        MAX-ACCESS      read-write
        STATUS          current
        DESCRIPTION
            "Maximum number of associated stations per IAP"
        ::= { global11bg 20 }

    global11bgIAPAutoCellByChan OBJECT-TYPE
        SYNTAX          INTEGER { enable(1) }
        MAX-ACCESS      read-write
        STATUS          current
        DESCRIPTION
            "Enable auto cell by channel"
        ::= { global11bg 21 }

--
-- INTERFACE IAP GLOBAL 11BG RATES
--

    rates11bgSet OBJECT-TYPE
        SYNTAX          INTEGER { default(1), optimize-range(2),
                                  optimize-throughput(3) }
        MAX-ACCESS      read-write
        STATUS          current
        DESCRIPTION
            "Set rates to a pre-defined set"
        ::= { rates11bg 1 }

    rates11bgTable OBJECT-TYPE
        SYNTAX          SEQUENCE OF Rates11bgEntry
        MAX-ACCESS      not-accessible
        STATUS          current
        DESCRIPTION
            "802.11bg Rates for the Array"
        ::= { rates11bg 2 }

    rates11bgEntry OBJECT-TYPE
        SYNTAX          Rates11bgEntry
        MAX-ACCESS      not-accessible
        STATUS          current
        DESCRIPTION
            "Rates table entry"
        INDEX       { rates11bgIndex }
        ::= { rates11bgTable 1 }

    Rates11bgEntry ::= SEQUENCE {
        rates11bgIndex      Integer32,
        rates11bgRate       DisplayString,
        rates11bgStatus     INTEGER
    }

    rates11bgIndex OBJECT-TYPE
        SYNTAX          Integer32
        MAX-ACCESS      not-accessible
        STATUS          current
        DESCRIPTION
            "Rates table index"
        ::= { rates11bgEntry 1 }

    rates11bgRate OBJECT-TYPE
        SYNTAX          DisplayString
        MAX-ACCESS      read-only
        STATUS          current
        DESCRIPTION
            "802.11bg rate"
        ::= { rates11bgEntry 2 }

    rates11bgStatus OBJECT-TYPE
        SYNTAX          INTEGER { disabled(0), basic(1), supported(2) }
        MAX-ACCESS      read-write
        STATUS          current
        DESCRIPTION
            "802.11bg rate status"
        ::= { rates11bgEntry 3 }

--
-- INTERFACE IAP GLOBAL 11BG AUTO CHANNEL LIST
--

    autoChannelList11bgSet OBJECT-TYPE
        SYNTAX          INTEGER { default(1), use-all(2) }
        MAX-ACCESS      read-write
        STATUS          current
        DESCRIPTION
            "Set channel list to defaults or all available channels"
        ::= { autoChannelList11bg 1 }

    autoChannelList11bgTable OBJECT-TYPE
        SYNTAX          SEQUENCE OF AutoChannelList11bgEntry
        MAX-ACCESS      not-accessible
        STATUS          current
        DESCRIPTION
            "802.11bg auto channel list"
        ::= { autoChannelList11bg 2 }

    autoChannelList11bgEntry OBJECT-TYPE
        SYNTAX          AutoChannelList11bgEntry
        MAX-ACCESS      not-accessible
        STATUS          current
        DESCRIPTION
            "Auto channel list entry"
        INDEX       { autoChannelList11bgIndex }
        ::= { autoChannelList11bgTable 1 }

    AutoChannelList11bgEntry ::= SEQUENCE {
        autoChannelList11bgIndex        Integer32,
        autoChannelList11bgChannel      Integer32,
        autoChannelList11bgStatus       INTEGER
    }

    autoChannelList11bgIndex OBJECT-TYPE
        SYNTAX          Integer32
        MAX-ACCESS      not-accessible
        STATUS          current
        DESCRIPTION
            "Auto channel list index"
        ::= { autoChannelList11bgEntry 1 }

    autoChannelList11bgChannel OBJECT-TYPE
        SYNTAX          Integer32
        MAX-ACCESS      read-only
        STATUS          current
        DESCRIPTION
            "Channel number"
        ::= { autoChannelList11bgEntry 2 }

    autoChannelList11bgStatus OBJECT-TYPE
        SYNTAX          INTEGER { disabled(0), enabled(1) }
        MAX-ACCESS      read-write
        STATUS          current
        DESCRIPTION
            "Channel status"
        ::= { autoChannelList11bgEntry 3 }

--
-- INTERFACE IAP WDS
--

    wdsAutoChannel OBJECT-TYPE
        SYNTAX          INTEGER { enable(1) }
        MAX-ACCESS      read-write
        STATUS          current
        DESCRIPTION
            "Automatically assign IAPs and channels for WDS client links"
        ::= { wds 1 }

    wdsClientLinkTableReset OBJECT-TYPE
        SYNTAX          INTEGER { reset(1) }
        MAX-ACCESS      read-write
        STATUS          current
        DESCRIPTION
            "Reset all WDS client links to off"
        ::= { wds 2 }

    wdsClientLinkTable OBJECT-TYPE
        SYNTAX          SEQUENCE OF WdsClientLinkEntry
        MAX-ACCESS      not-accessible
        STATUS          current
        DESCRIPTION
            "Table of WDS client links"
        ::= { wds 3 }

    wdsClientLinkEntry OBJECT-TYPE
        SYNTAX          WdsClientLinkEntry
        MAX-ACCESS      not-accessible
        STATUS          current
        DESCRIPTION
            "WDS client link table entry"
        INDEX       { wdsClientLinkIndex }
        ::= { wdsClientLinkTable 1 }

    WdsClientLinkEntry ::= SEQUENCE {
        wdsClientLinkIndex              Integer32,
        wdsClientLinkEnable             INTEGER,
        wdsClientLinkMaxIAPs            Integer32,
        wdsClientLinkTarget             DisplayString,
        wdsClientLinkSSID               DisplayString,
        wdsClientLinkUsername           DisplayString,
        wdsClientLinkPassword           DisplayString,
        wdsClientLinkPasswordForm       INTEGER
    }

    wdsClientLinkIndex OBJECT-TYPE
        SYNTAX          Integer32
        MAX-ACCESS      not-accessible
        STATUS          current
        DESCRIPTION
            "WDS client link table index"
        ::= { wdsClientLinkEntry 1 }

    wdsClientLinkEnable OBJECT-TYPE
        SYNTAX          INTEGER { disable(0), enable(1) }
        MAX-ACCESS      read-write
        STATUS          current
        DESCRIPTION
            "Enable/disable WDS client link"
        ::= { wdsClientLinkEntry 2 }

    wdsClientLinkMaxIAPs OBJECT-TYPE
        SYNTAX          Integer32(1..3)
        MAX-ACCESS      read-write
        STATUS          current
        DESCRIPTION
            "Maximum number of IAPs for WDS client link during auto channel"
        ::= { wdsClientLinkEntry 3 }

    wdsClientLinkTarget OBJECT-TYPE
        SYNTAX          DisplayString(SIZE(12..17))
        MAX-ACCESS      read-write
        STATUS          current
        DESCRIPTION
            "Base IAP MAC address of target array for WDS client link"
        ::= { wdsClientLinkEntry 4 }

    wdsClientLinkSSID OBJECT-TYPE
        SYNTAX          DisplayString(SIZE(1..32))
        MAX-ACCESS      read-write
        STATUS          current
        DESCRIPTION
            "SSID to use for association to target array"
        ::= { wdsClientLinkEntry 5 }

    wdsClientLinkUsername OBJECT-TYPE
        SYNTAX          DisplayString(SIZE(1..50))
        MAX-ACCESS      read-write
        STATUS          current
        DESCRIPTION
            "Username to use for association to target array"
        ::= { wdsClientLinkEntry 6 }

    wdsClientLinkPassword OBJECT-TYPE
        SYNTAX          DisplayString(SIZE(0..128))
        MAX-ACCESS      read-write
        STATUS          current
        DESCRIPTION
            "Password to use for association to target array"
        ::= { wdsClientLinkEntry 7 }

    wdsClientLinkPasswordForm OBJECT-TYPE
        SYNTAX          INTEGER { clear(0), encrypted(1) }
        MAX-ACCESS      read-write
        STATUS          current
        DESCRIPTION
            "Password form"
        ::= { wdsClientLinkEntry 8 }

    wdsHostLinkTable OBJECT-TYPE
        SYNTAX          SEQUENCE OF WdsHostLinkEntry
        MAX-ACCESS      not-accessible
        STATUS          current
        DESCRIPTION
            "Table of WDS host links"
        ::= { wds 4 }

    wdsHostLinkEntry OBJECT-TYPE
        SYNTAX          WdsHostLinkEntry
        MAX-ACCESS      not-accessible
        STATUS          current
        DESCRIPTION
            "WDS host link table entry"
        INDEX       { wdsHostLinkIndex }
        ::= { wdsHostLinkTable 1 }

    WdsHostLinkEntry ::= SEQUENCE {
        wdsHostLinkIndex            Integer32,
        wdsHostLinkState            INTEGER,
        wdsHostLinkNumIAPs          Integer32,
        wdsHostLinkSource           DisplayString,
        wdsHostLinkSSID             DisplayString
    }

    wdsHostLinkIndex OBJECT-TYPE
        SYNTAX          Integer32
        MAX-ACCESS      not-accessible
        STATUS          current
        DESCRIPTION
            "WDS host link table index"
        ::= { wdsHostLinkEntry 1 }

    wdsHostLinkState OBJECT-TYPE
        SYNTAX          INTEGER { disabled(0), enabled(1) }
        MAX-ACCESS      read-only
        STATUS          current
        DESCRIPTION
            "WDS host link state"
        ::= { wdsHostLinkEntry 2 }

    wdsHostLinkNumIAPs OBJECT-TYPE
        SYNTAX          Integer32
        MAX-ACCESS      read-only
        STATUS          current
        DESCRIPTION
            "Number of IAPs for WDS host link"
        ::= { wdsHostLinkEntry 3 }

    wdsHostLinkSource OBJECT-TYPE
        SYNTAX          DisplayString
        MAX-ACCESS      read-only
        STATUS          current
        DESCRIPTION
            "Base IAP MAC address of source array for WDS host link"
        ::= { wdsHostLinkEntry 4 }

    wdsHostLinkSSID OBJECT-TYPE
        SYNTAX          DisplayString
        MAX-ACCESS      read-only
        STATUS          current
        DESCRIPTION
            "WDS host link SSID"
        ::= { wdsHostLinkEntry 5 }

    wdsAllowStations OBJECT-TYPE
        SYNTAX          INTEGER { disable(0), enable(1) }
        MAX-ACCESS      read-write
        STATUS          current
        DESCRIPTION
            "Enable/disable stations on WDS host links"
        ::= { wds 5 }

    wdsStpEnable OBJECT-TYPE
        SYNTAX          INTEGER { disable(0), enable(1) }
        MAX-ACCESS      read-write
        STATUS          current
        DESCRIPTION
            "Enable/disable Spanning Tree Protocol on WDS links"
        ::= { wds 6 }

    wdsRoamThreshold OBJECT-TYPE
        SYNTAX          Integer32(1..20)
        MAX-ACCESS      read-write
        STATUS          current
        DESCRIPTION
            "Minimum RSSI difference (in dB) required to trigger a roam"
        ::= { wds 7 }

    wdsRoamAvgWeight OBJECT-TYPE
        SYNTAX          Integer32(0..99)
        MAX-ACCESS      read-write
        STATUS          current
        DESCRIPTION
            "RSSI averaging weight for roaming (0 = no averaging)"
        ::= { wds 8 }

--
-- INTERFACE IAP GLOBAL 11N
--

    global11nEnable OBJECT-TYPE
        SYNTAX          INTEGER { disable(0), enable(1) }
        MAX-ACCESS      read-write
        STATUS          current
        DESCRIPTION
            "Enable or disable 802.11n MIMO operation"
        ::= { global11n 1 }

    global11nTxChains OBJECT-TYPE
        SYNTAX          Integer32(1..4)
        MAX-ACCESS      read-write
        STATUS          current
        DESCRIPTION
            "Set number of TX chains used for 802.11n operation"
        ::= { global11n 2 }

    global11nRxChains OBJECT-TYPE
        SYNTAX          Integer32(1..4)
        MAX-ACCESS      read-write
        STATUS          current
        DESCRIPTION
            "Set number of RX chains used for 802.11n operation"
        ::= { global11n 3 }

    global11nGuardInterval OBJECT-TYPE
        SYNTAX          INTEGER { long(0), short(1) }
        MAX-ACCESS      read-write
        STATUS          current
        DESCRIPTION
            "Set 802.11n guard interval"
        ::= { global11n 4 }

    global11nAutoBond OBJECT-TYPE
        SYNTAX          INTEGER { disable(0), enable(1) }
        MAX-ACCESS      read-write
        STATUS          current
        DESCRIPTION
            "Enable or disable 802.11n 5GHz automatic channel bonding"
        ::= { global11n 5 }

    global11nBondedChannelWidth5GHz OBJECT-TYPE
        SYNTAX          INTEGER { dynamic(0), static(1) }
        MAX-ACCESS      read-write
        STATUS          current
        DESCRIPTION
            "Set 5GHz band 802.11n bonded channel width"
        ::= { global11n 6 }

    global11nBondedChannelWidth2GHz OBJECT-TYPE
        SYNTAX          INTEGER { dynamic(0), static(1) }
        MAX-ACCESS      read-write
        STATUS          current
        DESCRIPTION
            "Set 2.4GHz band 802.11n bonded channel width"
        ::= { global11n 7 }

    rates11n        OBJECT IDENTIFIER ::= { global11n 8 }

--
-- INTERFACE IAP GLOBAL 11N RATES
--

    rates11nSet OBJECT-TYPE
        SYNTAX          INTEGER { default(1) }
        MAX-ACCESS      read-write
        STATUS          current
        DESCRIPTION
            "Set 802.11n rates to a pre-defined set"
        ::= { rates11n 1 }

    rates11nTable OBJECT-TYPE
        SYNTAX          SEQUENCE OF Rates11nEntry
        MAX-ACCESS      not-accessible
        STATUS          current
        DESCRIPTION
            "Set 802.11n rates"
        ::= { rates11n 2 }

    rates11nEntry OBJECT-TYPE
        SYNTAX          Rates11nEntry
        MAX-ACCESS      not-accessible
        STATUS          current
        DESCRIPTION
            "Rates table entry"
        INDEX       { rates11nMCSIndex }
        ::= { rates11nTable 1 }

    Rates11nEntry ::= SEQUENCE {
        rates11nMCSIndex        Integer32,
        rates11nMCSStatus       INTEGER
    }

    rates11nMCSIndex OBJECT-TYPE
        SYNTAX          Integer32
        MAX-ACCESS      read-only
        STATUS          current
        DESCRIPTION
            "Modulation & coding scheme (MCS) index"
        ::= { rates11nEntry 1 }

    rates11nMCSStatus OBJECT-TYPE
        SYNTAX          INTEGER { disabled(0), basic(1), supported(2) }
        MAX-ACCESS      read-write
        STATUS          current
        DESCRIPTION
            "Set status for MCS index"
        ::= { rates11nEntry 2 }

    iapSsidToBssidMappingTable OBJECT-TYPE
        SYNTAX          SEQUENCE OF IapSsidToBssidMappingEntry
        MAX-ACCESS      not-accessible
        STATUS          current
        DESCRIPTION
            "SSID to BSSID mapping table"
        ::= { iap 7 }

    iapSsidToBssidMappingEntry OBJECT-TYPE
        SYNTAX          IapSsidToBssidMappingEntry
        MAX-ACCESS      not-accessible
        STATUS          current
        DESCRIPTION
            "SSID to BSSID mapping table entry"
        INDEX       { iapSsidToBssidMappingIndex }
        ::= { iapSsidToBssidMappingTable 1 }

    IapSsidToBssidMappingEntry ::= SEQUENCE {
        iapSsidToBssidMappingIndex          Integer32,
        iapSsidToBssidMappingIAP            DisplayString,
        iapSsidToBssidMappingSSID           DisplayString,
        iapSsidToBssidMappingBSSID          DisplayString
    }

    iapSsidToBssidMappingIndex OBJECT-TYPE
        SYNTAX          Integer32
        MAX-ACCESS      not-accessible
        STATUS          current
        DESCRIPTION
            "SSID to BSSID mapping table index"
        ::= { iapSsidToBssidMappingEntry 1 }

    iapSsidToBssidMappingIAP OBJECT-TYPE
        SYNTAX          DisplayString
        MAX-ACCESS      read-only
        STATUS          current
        DESCRIPTION
            "IAP name"
        ::= { iapSsidToBssidMappingEntry 2 }

    iapSsidToBssidMappingSSID OBJECT-TYPE
        SYNTAX          DisplayString
        MAX-ACCESS      read-only
        STATUS          current
        DESCRIPTION
            "SSID name"
        ::= { iapSsidToBssidMappingEntry 3 }

    iapSsidToBssidMappingBSSID OBJECT-TYPE
        SYNTAX          DisplayString
        MAX-ACCESS      read-only
        STATUS          current
        DESCRIPTION
            "BSSID for IAP/SSID specified"
        ::= { iapSsidToBssidMappingEntry 4 }

--
-- INTERFACE IAP GLOBAL 11AC
--

    global11acEnable OBJECT-TYPE
        SYNTAX          INTEGER { disable(0), enable(1) }
        MAX-ACCESS      read-write
        STATUS          current
        DESCRIPTION
            "Enable or disable 802.11ac MIMO operation"
        ::= { global11ac 1 }

    global11acGuardInterval OBJECT-TYPE
        SYNTAX          INTEGER { long(0), short(1) }
        MAX-ACCESS      read-write
        STATUS          current
        DESCRIPTION
            "Set 802.11ac guard interval"
        ::= { global11ac 2 }

    global11acMaxMCS1SS OBJECT-TYPE
        SYNTAX          INTEGER { mcs7(0), mcs8(1), mcs9(2) }
        MAX-ACCESS      read-write
        STATUS          current
        DESCRIPTION
            "Set max MCS for 1 spatial stream for 802.11ac operation"
        ::= { global11ac 3 }

    global11acMaxMCS2SS OBJECT-TYPE
        SYNTAX          INTEGER { mcs7(0), mcs8(1), mcs9(2) }
        MAX-ACCESS      read-write
        STATUS          current
        DESCRIPTION
            "Set max MCS for 2 spatial streams for 802.11ac operation"
        ::= { global11ac 4 }

    global11acMaxMCS3SS OBJECT-TYPE
        SYNTAX          INTEGER { mcs7(0), mcs8(1), mcs9(2) }
        MAX-ACCESS      read-write
        STATUS          current
        DESCRIPTION
            "Set max MCS for 3 spatial streams for 802.11ac operation"
        ::= { global11ac 5 }

    global11acMaxMCS4SS OBJECT-TYPE
        SYNTAX          INTEGER { mcs7(0), mcs8(1), mcs9(2) }
        MAX-ACCESS      read-write
        STATUS          current
        DESCRIPTION
            "Set max MCS for 4 spatial streams for 802.11ac operation"
        ::= { global11ac 6 }

    global11acTxBeamForming OBJECT-TYPE
        SYNTAX          INTEGER { disable(0), enable(1) }
        MAX-ACCESS      read-write
        STATUS          current
        DESCRIPTION
            "Enable or disable 802.11ac Wave 2 TX Beam Forming"
        ::= { global11ac 7 }

    global11acMultiUserMimo OBJECT-TYPE
        SYNTAX          INTEGER { disable(0), enable(1) }
        MAX-ACCESS      read-write
        STATUS          current
        DESCRIPTION
            "Enable or disable 802.11ac Wave 2 Multi-User MIMO"
        ::= { global11ac 8 }

    global11acWave2Capability OBJECT-TYPE
        SYNTAX          INTEGER { disabled(0), enabled(1) }
        MAX-ACCESS      read-only
        STATUS          current
        DESCRIPTION
            "Status of 802.11ac Wave 2 Capability"
        ::= { global11ac 9 }    

    global11acAutoBond OBJECT-TYPE
        SYNTAX          INTEGER { disable(0), enable(1) }
        MAX-ACCESS      read-write
        STATUS          current
        DESCRIPTION
            "Enable or disable 802.11ac 5GHz automatic channel bonding"
        ::= { global11ac 10 }


--
-- INTERFACE ETHERNET
--

    ethTable OBJECT-TYPE
        SYNTAX          SEQUENCE OF EthEntry
        MAX-ACCESS      not-accessible
        STATUS          current
        DESCRIPTION
            "Table of ethernet interfaces"
        ::= { ethernet 1 }

    ethEntry OBJECT-TYPE
        SYNTAX          EthEntry
        MAX-ACCESS      not-accessible
        STATUS          current
        DESCRIPTION
            "Ethernet table entry"
        INDEX       { ethIndex }
        ::= { ethTable 1 }

    EthEntry ::= SEQUENCE {
        ethIndex            Integer32,
        ethName             DisplayString,
        ethEnable           INTEGER,
        ethDHCPBind         INTEGER,
        ethIPAddress        IpAddress,
        ethIPMask           IpAddress,
        ethGateway          IpAddress,
        ethAutoneg          INTEGER,
        ethDuplex           INTEGER,
        ethSpeed            INTEGER,
        ethMTU              Integer32,
        ethMgmt             INTEGER,
        ethDefault          INTEGER,
        ethPortMode         INTEGER,
        ethBond             DisplayString,
        ethLED              INTEGER
    }

    ethIndex OBJECT-TYPE
        SYNTAX          Integer32
        MAX-ACCESS      not-accessible
        STATUS          current
        DESCRIPTION
            "Ethernet table index"
        ::= { ethEntry 1 }

    ethName OBJECT-TYPE
        SYNTAX          DisplayString
        MAX-ACCESS      read-only
        STATUS          current
        DESCRIPTION
            "Ethernet interface name"
        ::= { ethEntry 2 }

    ethEnable OBJECT-TYPE
        SYNTAX          INTEGER { down(0), up (1) }
        MAX-ACCESS      read-write
        STATUS          current
        DESCRIPTION
            "Enable or disable this interface"
        ::= { ethEntry 3 }

    ethDHCPBind OBJECT-TYPE
        SYNTAX          INTEGER { disable(0), enable(1) }
        MAX-ACCESS      read-write
        STATUS          current
        DESCRIPTION
            "Use DHCP"
        ::= { ethEntry 4 }

    ethIPAddress OBJECT-TYPE
        SYNTAX          IpAddress
        MAX-ACCESS      read-write
        STATUS          current
        DESCRIPTION
            "IP address"
        ::= { ethEntry 5 }

    ethIPMask OBJECT-TYPE
        SYNTAX          IpAddress
        MAX-ACCESS      read-write
        STATUS          current
        DESCRIPTION
            "IP Mask"
        ::= { ethEntry 6 }

    ethGateway OBJECT-TYPE
        SYNTAX          IpAddress
        MAX-ACCESS      read-write
        STATUS          current
        DESCRIPTION
            "Gateway IP address"
        ::= { ethEntry 7 }

    ethAutoneg OBJECT-TYPE
        SYNTAX          INTEGER { disable(0), enable(1) }
        MAX-ACCESS      read-write
        STATUS          current
        DESCRIPTION
            "Enable/disable autonegotiation"
        ::= { ethEntry 8 }

    ethDuplex OBJECT-TYPE
        SYNTAX          INTEGER { half(0), full(1) }
        MAX-ACCESS      read-write
        STATUS          current
        DESCRIPTION
            "Duplex settings"
        ::= { ethEntry 9 }

    ethSpeed OBJECT-TYPE
        SYNTAX          INTEGER { speed-10Mbps(1), speed-100Mbps(2), speed-1000Mbps(3), speed-2500Mbps(4) }
        MAX-ACCESS      read-write
        STATUS          current
        DESCRIPTION
            "Speed settings: 10 and 100 for fast eth, 100, 1000, and 2500 for gig eth"
        ::= { ethEntry 10 }

    ethMTU OBJECT-TYPE
        SYNTAX          Integer32(64..1732)
        MAX-ACCESS      read-write
        STATUS          current
        DESCRIPTION
            "MTU size"
        ::= { ethEntry 11 }

    ethMgmt OBJECT-TYPE
        SYNTAX          INTEGER { disable(0), enable(1) }
        MAX-ACCESS      read-write
        STATUS          current
        DESCRIPTION
            "Enable/disable management (gig eth only)"
        ::= { ethEntry 12 }

    ethDefault OBJECT-TYPE
        SYNTAX          INTEGER { reset(1) }
        MAX-ACCESS      read-write
        STATUS          current
        DESCRIPTION
            "Reset to default values"
        ::= { ethEntry 13 }

    ethPortMode OBJECT-TYPE
        SYNTAX          INTEGER { link-backup(0), load-balance(3), bridge(4),
                                  ieee802dot3ad(5), broadcast(6), mirror(7) }
        MAX-ACCESS      read-write
        STATUS          current
        DESCRIPTION
            "Select the configuration of the gig eth ports"
        ::= { ethEntry 14 }

    ethBond OBJECT-TYPE
        SYNTAX          DisplayString(SIZE(1..20))
        MAX-ACCESS      read-write
        STATUS          current
        DESCRIPTION
            "Specify bond for this gig eth port"
        ::= { ethEntry 15 }

    ethLED OBJECT-TYPE
        SYNTAX          INTEGER { disable(0), enable(1) }
        MAX-ACCESS      read-write
        STATUS          current
        DESCRIPTION
            "Enable/disable LED operation"
        ::= { ethEntry 16 }

    bondTable OBJECT-TYPE
        SYNTAX          SEQUENCE OF BondEntry
        MAX-ACCESS      not-accessible
        STATUS          current
        DESCRIPTION
            "Table of bond interfaces"
        ::= { ethernet 2 }

    bondEntry OBJECT-TYPE
        SYNTAX          BondEntry
        MAX-ACCESS      not-accessible
        STATUS          current
        DESCRIPTION
            "Bond table entry"
        INDEX       { bondIndex }
        ::= { bondTable 1 }

    BondEntry ::= SEQUENCE {
        bondIndex           Integer32,
        bondName            DisplayString,
        bondMode            INTEGER,
        bondMirror          DisplayString,
        bondActiveVlans     DisplayString
    }

    bondIndex OBJECT-TYPE
        SYNTAX          Integer32
        MAX-ACCESS      not-accessible
        STATUS          current
        DESCRIPTION
            "Bond table index"
        ::= { bondEntry 1 }

    bondName OBJECT-TYPE
        SYNTAX          DisplayString
        MAX-ACCESS      read-only
        STATUS          current
        DESCRIPTION
            "Bond name"
        ::= { bondEntry 2 }

    bondMode OBJECT-TYPE
        SYNTAX          INTEGER { link-backup(0), load-balance(3),
                                  ieee802dot3ad(5), broadcast(6) }
        MAX-ACCESS      read-write
        STATUS          current
        DESCRIPTION
            "Bond mode"
        ::= { bondEntry 3 }

    bondMirror OBJECT-TYPE
        SYNTAX          DisplayString(SIZE(0..20))
        MAX-ACCESS      read-write
        STATUS          current
        DESCRIPTION
            "Specify mirror bond to mirror traffic"
        ::= { bondEntry 4 }

    bondActiveVlans OBJECT-TYPE
        SYNTAX          DisplayString(SIZE(0..160))
        MAX-ACCESS      read-write
        STATUS          current
        DESCRIPTION
            "Specify VLANs active on bond"
        ::= { bondEntry 5 }

--
-- INTERFACE CONSOLE
--

    consoleBaud OBJECT-TYPE
        SYNTAX          Integer32(300..115200)
        MAX-ACCESS      read-write
        STATUS          current
        DESCRIPTION
            "Baud rate"
        ::= { console 1 }

    consoleByteSize OBJECT-TYPE
        SYNTAX          Integer32(7..8)
        MAX-ACCESS      read-write
        STATUS          current
        DESCRIPTION
            "Byte/word size in bits"
        ::= { console 2 }

    consoleParity OBJECT-TYPE
        SYNTAX          INTEGER { none(0), odd(1), even(2) }
        MAX-ACCESS      read-write
        STATUS          current
        DESCRIPTION
            "Number of parity bits"
        ::= { console 3 }

    consoleStopBits OBJECT-TYPE
        SYNTAX          Integer32(1..2)
        MAX-ACCESS      read-write
        STATUS          current
        DESCRIPTION
            "Number of stop bits"
        ::= { console 4 }

    consoleTimeout OBJECT-TYPE
        SYNTAX          Integer32(30..100000)
        MAX-ACCESS      read-write
        STATUS          current
        DESCRIPTION
            "Inactivity timeout"
        ::= { console 5 }

    consoleMgmt OBJECT-TYPE
        SYNTAX          INTEGER { disable(0), enable(1) }
        MAX-ACCESS      read-write
        STATUS          current
        DESCRIPTION
            "Enable or disable management"
        ::= { console 6 }

--
-- NETWORK MAP
--

    neighborArrayTable OBJECT-TYPE
        SYNTAX          SEQUENCE OF NeighborArrayEntry
        MAX-ACCESS      not-accessible
        STATUS          current
        DESCRIPTION
            "Table of neighbor arrays seen by our array"
        ::= { networkMap 1 }

    neighborArrayEntry OBJECT-TYPE
        SYNTAX          NeighborArrayEntry
        MAX-ACCESS      not-accessible
        STATUS          current
        DESCRIPTION
            "Table entry for neighbor array"
        INDEX       { neighborArrayIndex }
        ::= { neighborArrayTable 1 }

    NeighborArrayEntry ::= SEQUENCE {
        neighborArrayIndex                  Integer32,
        neighborArrayHostname               DisplayString,
        neighborArrayLocation               DisplayString,
        neighborArrayIPAddress              DisplayString,
        neighborArrayModel                  DisplayString,
        neighborArrayNumIAPsUp              Integer32,
        neighborArrayNumSSIDs               Integer32,
        neighborArrayNumActiveSSIDs         Integer32,
        neighborArrayNumStationsAssoc       Integer32,
        neighborArrayInRange                INTEGER,
        neighborArrayFastRoam               INTEGER,
        neighborArrayUptime                 DisplayString
    }

    neighborArrayIndex OBJECT-TYPE
        SYNTAX          Integer32
        MAX-ACCESS      not-accessible
        STATUS          current
        DESCRIPTION
            "Neighbor array index"
        ::= { neighborArrayEntry 1 }

    neighborArrayHostname OBJECT-TYPE
        SYNTAX          DisplayString
        MAX-ACCESS      read-only
        STATUS          current
        DESCRIPTION
            "Hostname of the neighbor array"
        ::= { neighborArrayEntry 2 }

    neighborArrayLocation OBJECT-TYPE
        SYNTAX          DisplayString
        MAX-ACCESS      read-only
        STATUS          current
        DESCRIPTION
            "Location of the neighbor array"
        ::= { neighborArrayEntry 3 }

    neighborArrayIPAddress OBJECT-TYPE
        SYNTAX          DisplayString
        MAX-ACCESS      read-only
        STATUS          current
        DESCRIPTION
            "IP Address of the neighbor array"
        ::= { neighborArrayEntry 4 }

    neighborArrayModel OBJECT-TYPE
        SYNTAX          DisplayString
        MAX-ACCESS      read-only
        STATUS          current
        DESCRIPTION
            "Model of the neighbor array"
        ::= { neighborArrayEntry 5 }

    neighborArrayNumIAPsUp OBJECT-TYPE
        SYNTAX          Integer32
        MAX-ACCESS      read-only
        STATUS          current
        DESCRIPTION
            "Number of IAPs enabled on the neighbor array"
        ::= { neighborArrayEntry 6 }

    neighborArrayNumSSIDs OBJECT-TYPE
        SYNTAX          Integer32
        MAX-ACCESS      read-only
        STATUS          current
        DESCRIPTION
            "Number of SSIDs defined on the neighbor array"
        ::= { neighborArrayEntry 7 }

    neighborArrayNumActiveSSIDs OBJECT-TYPE
        SYNTAX          Integer32
        MAX-ACCESS      read-only
        STATUS          current
        DESCRIPTION
            "Number of active SSIDs on the neighbor array"
        ::= { neighborArrayEntry 8 }

    neighborArrayNumStationsAssoc OBJECT-TYPE
        SYNTAX          Integer32
        MAX-ACCESS      read-only
        STATUS          current
        DESCRIPTION
            "Number of stations associated with the neighbor array"
        ::= { neighborArrayEntry 9 }

    neighborArrayInRange OBJECT-TYPE
        SYNTAX          INTEGER { not-in-range(0), in-range(1) }
        MAX-ACCESS      read-only
        STATUS          current
        DESCRIPTION
            "Flag indicating whether neighbor array is in our range"
        ::= { neighborArrayEntry 10 }

    neighborArrayFastRoam OBJECT-TYPE
        SYNTAX          INTEGER { no-fast-roam(0), fast-roam(1) }
        MAX-ACCESS      read-only
        STATUS          current
        DESCRIPTION
            "Flag indicating whether stations can fast roam between us and neighbor array"
        ::= { neighborArrayEntry 11 }

    neighborArrayUptime OBJECT-TYPE
        SYNTAX          DisplayString
        MAX-ACCESS      read-only
        STATUS          current
        DESCRIPTION
            "Uptime (in D:H:M) of the neighbor array"
        ::= { neighborArrayEntry 12 }

--
-- RADIUS
--

    radiusEnable OBJECT-TYPE
        SYNTAX          INTEGER { external(1), internal(2), active-directory(3) }
        MAX-ACCESS      read-write
        STATUS          current
        DESCRIPTION
            "Radius server enabled"
        ::= { radius 1 }

    radiusServerExternal    OBJECT IDENTIFIER ::= { radius 2 }
    radiusServerInternal    OBJECT IDENTIFIER ::= { radius 3 }
    radiusServerAD          OBJECT IDENTIFIER ::= { radius 4 }

--
-- RADIUS SERVER EXTERNAL
--

    radiusPriServerIPAddress OBJECT-TYPE
        SYNTAX          IpAddress
        MAX-ACCESS      read-write
        STATUS          current
        DESCRIPTION
            "Primary Radius server IP address"
        ::= { radiusServerExternal 1 }

    radiusPriServerPort OBJECT-TYPE
        SYNTAX          Integer32(0..65535)
        MAX-ACCESS      read-write
        STATUS          current
        DESCRIPTION
            "Primary Radius server port"
        ::= { radiusServerExternal 2 }

    radiusPriServerSecret OBJECT-TYPE
        SYNTAX          DisplayString(SIZE(0..64))
        MAX-ACCESS      read-write
        STATUS          current
        DESCRIPTION
            "Primary Radius server secret"
        ::= { radiusServerExternal 3 }

    radiusSecServerIPAddress OBJECT-TYPE
        SYNTAX          IpAddress
        MAX-ACCESS      read-write
        STATUS          current
        DESCRIPTION
            "Secondary Radius server IP address"
        ::= { radiusServerExternal 4 }

    radiusSecServerPort OBJECT-TYPE
        SYNTAX          Integer32(0..65535)
        MAX-ACCESS      read-write
        STATUS          current
        DESCRIPTION
            "Secondary Radius server port"
        ::= { radiusServerExternal 5 }

    radiusSecServerSecret OBJECT-TYPE
        SYNTAX          DisplayString(SIZE(0..64))
        MAX-ACCESS      read-write
        STATUS          current
        DESCRIPTION
            "Secondary Radius server secret"
        ::= { radiusServerExternal 6 }

    radiusTimeout OBJECT-TYPE
        SYNTAX          Integer32(0..65535)
        MAX-ACCESS      read-write
        STATUS          current
        DESCRIPTION
            "Timeout until the primary server is retired _ given up on"
        ::= { radiusServerExternal 7 }

    radiusAcctEnable OBJECT-TYPE
        SYNTAX          INTEGER { disable(0), enable(1) }
        MAX-ACCESS      read-write
        STATUS          current
        DESCRIPTION
            "Enable or disable Radius Accounting"
        ::= { radiusServerExternal 8 }

    radiusAcctPriServerIPAddress OBJECT-TYPE
        SYNTAX          IpAddress
        MAX-ACCESS      read-write
        STATUS          current
        DESCRIPTION
            "Primary Radius Accounting server IP address"
        ::= { radiusServerExternal 9 }

    radiusAcctPriServerPort OBJECT-TYPE
        SYNTAX          Integer32(0..65535)
        MAX-ACCESS      read-write
        STATUS          current
        DESCRIPTION
            "Primary Radius Accounting server port"
        ::= { radiusServerExternal 10 }

    radiusAcctPriServerSecret OBJECT-TYPE
        SYNTAX          DisplayString(SIZE(0..64))
        MAX-ACCESS      read-write
        STATUS          current
        DESCRIPTION
            "Primary Radius Accounting server secret"
        ::= { radiusServerExternal 11 }

    radiusAcctSecServerIPAddress OBJECT-TYPE
        SYNTAX          IpAddress
        MAX-ACCESS      read-write
        STATUS          current
        DESCRIPTION
            "Secondary Radius Accounting server IP address"
        ::= { radiusServerExternal 12 }

    radiusAcctSecServerPort OBJECT-TYPE
        SYNTAX          Integer32(0..65535)
        MAX-ACCESS      read-write
        STATUS          current
        DESCRIPTION
            "Secondary Radius Accounting server port"
        ::= { radiusServerExternal 13 }

    radiusAcctSecServerSecret OBJECT-TYPE
        SYNTAX          DisplayString(SIZE(0..64))
        MAX-ACCESS      read-write
        STATUS          current
        DESCRIPTION
            "Secondary Radius Accounting server secret"
        ::= { radiusServerExternal 14 }

    radiusAcctInterval OBJECT-TYPE
        SYNTAX          Integer32(60..65535)
        MAX-ACCESS      read-write
        STATUS          current
        DESCRIPTION
            "Interim accounting update interval"
        ::= { radiusServerExternal 15 }

    radiusNasIdentifier OBJECT-TYPE
        SYNTAX          DisplayString(SIZE(0.. 255))
        MAX-ACCESS      read-write
        STATUS          current
        DESCRIPTION
            "Radius NAS Identifier"
        ::= { radiusServerExternal 16 }

    radiusPriServerHostname OBJECT-TYPE
        SYNTAX          DisplayString(SIZE(0.. 255))
        MAX-ACCESS      read-write
        STATUS          current
        DESCRIPTION
            "Primary Radius server hostname"
        ::= { radiusServerExternal 17 }

    radiusSecServerHostname OBJECT-TYPE
        SYNTAX          DisplayString(SIZE(0.. 255))
        MAX-ACCESS      read-write
        STATUS          current
        DESCRIPTION
            "Secondary Radius server hostname"
        ::= { radiusServerExternal 18 }

    radiusAcctPriServerHostname OBJECT-TYPE
        SYNTAX          DisplayString(SIZE(0.. 255))
        MAX-ACCESS      read-write
        STATUS          current
        DESCRIPTION
            "Primary Radius Accounting server hostname"
        ::= { radiusServerExternal 19 }

    radiusAcctSecServerHostname OBJECT-TYPE
        SYNTAX          DisplayString(SIZE(0.. 255))
        MAX-ACCESS      read-write
        STATUS          current
        DESCRIPTION
            "Secondary Radius Accounting server hostname"
        ::= { radiusServerExternal 20 }

    radiusPriServerSecretEnc OBJECT-TYPE
        SYNTAX          DisplayString(SIZE(0..128))
        MAX-ACCESS      read-write
        STATUS          current
        DESCRIPTION
            "Primary Radius server secret (encrypted)"
        ::= { radiusServerExternal 21 }

    radiusSecServerSecretEnc OBJECT-TYPE
        SYNTAX          DisplayString(SIZE(0..128))
        MAX-ACCESS      read-write
        STATUS          current
        DESCRIPTION
            "Secondary Radius server secret (encrypted)"
        ::= { radiusServerExternal 22 }

    radiusAcctPriServerSecretEnc OBJECT-TYPE
        SYNTAX          DisplayString(SIZE(0..128))
        MAX-ACCESS      read-write
        STATUS          current
        DESCRIPTION
            "Primary Radius Accounting server secret (encrypted)"
        ::= { radiusServerExternal 23 }

    radiusAcctSecServerSecretEnc OBJECT-TYPE
        SYNTAX          DisplayString(SIZE(0..128))
        MAX-ACCESS      read-write
        STATUS          current
        DESCRIPTION
            "Secondary Radius Accounting server secret (encrypted)"
        ::= { radiusServerExternal 24 }

    radiusDASPort OBJECT-TYPE
        SYNTAX          Integer32(0..65535)
        MAX-ACCESS      read-write
        STATUS          current
        DESCRIPTION
            "RADIUS Dynamic Authorization port"
        ::= { radiusServerExternal 25 }

    radiusDASTimeWindow OBJECT-TYPE
        SYNTAX          Integer32(5..10000000)
        MAX-ACCESS      read-write
        STATUS          current
        DESCRIPTION
            "RADIUS Dynamic Authorization time window (in seconds)"
        ::= { radiusServerExternal 26 }

    radiusDASEventTimestamp OBJECT-TYPE
        SYNTAX          INTEGER { optional(0), required(1) }
        MAX-ACCESS      read-write
        STATUS          current
        DESCRIPTION
            "Specify whether Event-Timestamp attribute is required for RADIUS Dynamic Authorization replay protection"
        ::= { radiusServerExternal 27 }

    radiusCalledStationIdFormat OBJECT-TYPE
        SYNTAX          INTEGER { bssid-ssid(0), bssid(1), ethernet-mac(2) }
        MAX-ACCESS      read-write
        STATUS          current
        DESCRIPTION
            "Specify Called-Station-Id attribute format used in RADIUS packets"
        ::= { radiusServerExternal 28 }

    radiusStationMACFormat OBJECT-TYPE
        SYNTAX          INTEGER { lower(0), upper(1), lower-hyphen(2), upper-hyphen(3) }
        MAX-ACCESS      read-write
        STATUS          current
        DESCRIPTION
            "Specify station MAC address format used in a User-Name attribute during RADIUS MAC authentication"
        ::= { radiusServerExternal 29 }

    radiusFailoverTimeout OBJECT-TYPE
        SYNTAX          Integer32(10..600)
        MAX-ACCESS      read-write
        STATUS          current
        DESCRIPTION
            "Timeout before failover to another server after current server failed"
        ::= { radiusServerExternal 30 }

--
-- RADIUS SERVER INTERNAL
--

    radiusUserTable OBJECT-TYPE
        SYNTAX          SEQUENCE OF RadiusUserEntry
        MAX-ACCESS      not-accessible
        STATUS          current
        DESCRIPTION
            "Table containing Radius User details"
        ::= { radiusServerInternal 1 }

    radiusUserEntry OBJECT-TYPE
        SYNTAX          RadiusUserEntry
        MAX-ACCESS      not-accessible
        STATUS          current
        DESCRIPTION
            "Radius user table entry"
        INDEX       { radiusUserIndex }
        ::= { radiusUserTable 1 }

    RadiusUserEntry ::= SEQUENCE {
        radiusUserIndex         Integer32,
        radiusUserID            DisplayString,
        radiusUserPassword      DisplayString,
        radiusUserSSID          DisplayString,
        radiusUserRowStatus     RowStatus,
        radiusUserGroup         DisplayString,
        radiusUserPasswordForm  INTEGER
    }

    radiusUserIndex OBJECT-TYPE
        SYNTAX          Integer32
        MAX-ACCESS      not-accessible
        STATUS          current
        DESCRIPTION
            "Radius user table index"
        ::= { radiusUserEntry 1 }

    radiusUserID OBJECT-TYPE
        SYNTAX          DisplayString(SIZE(1..50))
        MAX-ACCESS      read-create
        STATUS          current
        DESCRIPTION
            "Radius user ID"
        ::= { radiusUserEntry 2 }

    radiusUserPassword OBJECT-TYPE
        SYNTAX          DisplayString(SIZE(1..100))
        MAX-ACCESS      read-create
        STATUS          current
        DESCRIPTION
            "Radius user password"
        ::= { radiusUserEntry 3 }

    radiusUserSSID OBJECT-TYPE
        SYNTAX          DisplayString(SIZE(0..32))
        MAX-ACCESS      read-create
        STATUS          current
        DESCRIPTION
            "Radius user SSID"
        ::= { radiusUserEntry 4 }

    radiusUserRowStatus OBJECT-TYPE
        SYNTAX          RowStatus
        MAX-ACCESS      read-create
        STATUS          current
        DESCRIPTION
            "Status of the radius user table entry"
        ::= { radiusUserEntry 5 }

    radiusUserGroup OBJECT-TYPE
        SYNTAX          DisplayString(SIZE(0..32))
        MAX-ACCESS      read-create
        STATUS          current
        DESCRIPTION
            "Radius user group"
        ::= { radiusUserEntry 6 }

    radiusUserPasswordForm OBJECT-TYPE
        SYNTAX          INTEGER { clear(0), encrypted(1) }
        MAX-ACCESS      read-create
        STATUS          current
        DESCRIPTION
            "Password form"
        ::= { radiusUserEntry 7 }

    radiusUserTableReset OBJECT-TYPE
        SYNTAX          INTEGER { reset(1) }
        MAX-ACCESS      read-write
        STATUS          current
        DESCRIPTION
            "Reset Radius user table (clear all entries)"
        ::= { radiusServerInternal 2 }

--
-- RADIUS SERVER ACTIVE DIRECTORY
--

    activeDirectoryUser OBJECT-TYPE
        SYNTAX          DisplayString(SIZE(0..20))
        MAX-ACCESS      read-write
        STATUS          current
        DESCRIPTION
            "Active Directory domain administrator user name"
        ::= { radiusServerAD 1 }

    activeDirectoryPassword OBJECT-TYPE
        SYNTAX          DisplayString(SIZE(0..20))
        MAX-ACCESS      read-write
        STATUS          current
        DESCRIPTION
            "Active Directory domain administrator password"
        ::= { radiusServerAD 2 }

    activeDirectoryDomainController OBJECT-TYPE
        SYNTAX          DisplayString(SIZE(0..255))
        MAX-ACCESS      read-write
        STATUS          current
        DESCRIPTION
            "Active Directory domain controller"
        ::= { radiusServerAD 3 }

    activeDirectoryWorkgroup OBJECT-TYPE
        SYNTAX          DisplayString(SIZE(0..255))
        MAX-ACCESS      read-write
        STATUS          current
        DESCRIPTION
            "Active Directory workgroup"
        ::= { radiusServerAD 4 }

    activeDirectoryRealm OBJECT-TYPE
        SYNTAX          DisplayString(SIZE(0..255))
        MAX-ACCESS      read-write
        STATUS          current
        DESCRIPTION
            "Active Directory realm"
        ::= { radiusServerAD 5 }

    activeDirectoryJoin OBJECT-TYPE
        SYNTAX          INTEGER { join(1) }
        MAX-ACCESS      read-write
        STATUS          current
        DESCRIPTION
            "Join Active Directory domain"
        ::= { radiusServerAD 6 }

    activeDirectoryLeave OBJECT-TYPE
        SYNTAX          INTEGER { leave(1) }
        MAX-ACCESS      read-write
        STATUS          current
        DESCRIPTION
            "Leave Active Directory domain"
        ::= { radiusServerAD 7 }

--
-- ROAM ASSIST
--

    roamAssistEnable OBJECT-TYPE
        SYNTAX          INTEGER { disable(0), enable(1) }
        MAX-ACCESS      read-write
        STATUS          current
        DESCRIPTION
            "Enable or disable roaming assist"
        ::= { roamAssist 1 }

    roamAssistPeriod OBJECT-TYPE
        SYNTAX          Integer32(60..9999)
        MAX-ACCESS      read-write
        STATUS          current
        DESCRIPTION
            "Roaming assist backoff period (in seconds)"
        ::= { roamAssist 2 }

    roamAssistThreshold OBJECT-TYPE
        SYNTAX          Integer32(-50..50)
        MAX-ACCESS      read-write
        STATUS          current
        DESCRIPTION
            "Roaming RSSI threshold in db relative to nearest array RSSI"
        ::= { roamAssist 3 }

    roamAssistDataRate OBJECT-TYPE
        SYNTAX          Integer32(1..99)
        MAX-ACCESS      read-write
        STATUS          current
        DESCRIPTION
            "Minimum packet data rate before roaming (in Mbps)"
        ::= { roamAssist 4 }

    roamAssistDevices OBJECT-TYPE
        SYNTAX          DisplayString(SIZE(0..255))
        MAX-ACCESS      read-write
        STATUS          current
        DESCRIPTION
            "Device types or classes to assist"
        ::= { roamAssist 5 }

--
-- SECURITY
--

    wep     OBJECT IDENTIFIER ::= { security 1 }
    wpa     OBJECT IDENTIFIER ::= { security 2 }

--
-- SECURITY WEP
--

    wepDefaultKeyID OBJECT-TYPE
        SYNTAX          Integer32(1..4)
        MAX-ACCESS      read-write
        STATUS          current
        DESCRIPTION
            "Default encryption key id for WEP"
        ::= { wep 1 }

    wepKeyTable OBJECT-TYPE
        SYNTAX          SEQUENCE OF WepKeyEntry
        MAX-ACCESS      not-accessible
        STATUS          current
        DESCRIPTION
            "WEP encryption key table for the Array"
        ::= { wep 2 }

    wepKeyEntry OBJECT-TYPE
        SYNTAX          WepKeyEntry
        MAX-ACCESS      not-accessible
        STATUS          current
        DESCRIPTION
            "WEP key table entry"
        INDEX       { wepKeyNum }
        ::= { wepKeyTable 1 }

    WepKeyEntry ::= SEQUENCE {
        wepKeyNum           Integer32,
        wepKeySize          INTEGER,
        wepKeyString        DisplayString,
        wepKeyStringForm    INTEGER
    }

    wepKeyNum OBJECT-TYPE
        SYNTAX          Integer32
        MAX-ACCESS      read-only
        STATUS          current
        DESCRIPTION
            "WEP key number"
        ::= { wepKeyEntry 1 }

    wepKeySize OBJECT-TYPE
        SYNTAX          INTEGER{ wep40(1), wep128(2) }
        MAX-ACCESS      read-only
        STATUS          current
        DESCRIPTION
            "WEP key size - 40 or 128 bits"
        ::= { wepKeyEntry 2 }

    wepKeyString OBJECT-TYPE
        SYNTAX          DisplayString(SIZE(0..26))
        MAX-ACCESS      read-write
        STATUS          current
        DESCRIPTION
            "WEP encryption key"
        ::= { wepKeyEntry 3 }

    wepKeyStringForm OBJECT-TYPE
        SYNTAX          INTEGER { clear(0), encrypted(1) }
        MAX-ACCESS      read-write
        STATUS          current
        DESCRIPTION
            "Key string form"
        ::= { wepKeyEntry 4 }

--
-- SECURITY WPA
--

    wpaTKIP OBJECT-TYPE
        SYNTAX          INTEGER { disable(0), enable(1) }
        MAX-ACCESS      read-write
        STATUS          current
        DESCRIPTION
            "TKIP enable or disable"
        ::= { wpa 1 }

    wpaAES OBJECT-TYPE
        SYNTAX          INTEGER { disable(0), enable(1) }
        MAX-ACCESS      read-write
        STATUS          current
        DESCRIPTION
            "AES enable or disable"
        ::= { wpa 2 }

    wpaEAP OBJECT-TYPE
        SYNTAX          INTEGER { disable(0), enable(1) }
        MAX-ACCESS      read-write
        STATUS          current
        DESCRIPTION
            "EAP enable or disable"
        ::= { wpa 3 }

    wpaPSK OBJECT-TYPE
        SYNTAX          INTEGER { disable(0), enable(1) }
        MAX-ACCESS      read-write
        STATUS          current
        DESCRIPTION
            "PSK enable or disable"
        ::= { wpa 4 }

    wpaPassphrase OBJECT-TYPE
        SYNTAX          DisplayString(SIZE(0|8..64))
        MAX-ACCESS      read-write
        STATUS          current
        DESCRIPTION
            "PSK ASCII passphrase or Hex key"
        ::= { wpa 5 }

    wpaRekey OBJECT-TYPE
        SYNTAX          Integer32(0..1000000)
        MAX-ACCESS      read-write
        STATUS          current
        DESCRIPTION
            "Rekey every 60 to 1000000 seconds, 0 - never"
        ::= { wpa 6 }

    wpaPassphraseEnc OBJECT-TYPE
        SYNTAX          DisplayString(SIZE(16..128))
        MAX-ACCESS      read-write
        STATUS          current
        DESCRIPTION
            "PSK ASCII passphrase or Hex key (encrypted)"
        ::= { wpa 7 }

--
-- SNMP AGENT
--

    snmpAgentEnable OBJECT-TYPE
        SYNTAX          INTEGER { disable(0), enable(1) }
        MAX-ACCESS      read-write
        STATUS          current
        DESCRIPTION
            "Enable or disable SNMPv2"
        ::= { snmpAgent 1 }

    snmpAgentReadWriteCommunity OBJECT-TYPE
        SYNTAX          DisplayString(SIZE(0..50))
        MAX-ACCESS      read-write
        STATUS          current
        DESCRIPTION
            "SNMP read-write community string"
        ::= { snmpAgent 2 }

    snmpAgentTrapHost OBJECT-TYPE
        SYNTAX          DisplayString(SIZE(0..255))
        MAX-ACCESS      read-write
        STATUS          current
        DESCRIPTION
            "SNMP trap IP address or host name"
        ::= { snmpAgent 3 }

    snmpAgentTrapPort OBJECT-TYPE
        SYNTAX          Integer32(0..65535)
        MAX-ACCESS      read-write
        STATUS          current
        DESCRIPTION
            "SNMP trap port"
        ::= { snmpAgent 4 }

    snmpAgentTrapAuth OBJECT-TYPE
        SYNTAX          INTEGER { disable(0), enable(1) }
        MAX-ACCESS      read-write
        STATUS          current
        DESCRIPTION
            "Enable/disable traps for authentication failures"
        ::= { snmpAgent 5 }

    snmpAgentReadOnlyCommunity OBJECT-TYPE
        SYNTAX          DisplayString(SIZE(0..50))
        MAX-ACCESS      read-write
        STATUS          current
        DESCRIPTION
            "SNMP read-only community string"
        ::= { snmpAgent 6 }

    snmpAgentTrapHost2 OBJECT-TYPE
        SYNTAX          DisplayString(SIZE(0..255))
        MAX-ACCESS      read-write
        STATUS          current
        DESCRIPTION
            "SNMP trap IP address or host name (host 2)"
        ::= { snmpAgent 7 }

    snmpAgentTrapPort2 OBJECT-TYPE
        SYNTAX          Integer32(0..65535)
        MAX-ACCESS      read-write
        STATUS          current
        DESCRIPTION
            "SNMP trap port (host 2)"
        ::= { snmpAgent 8 }

    snmpAgentTrapHost3 OBJECT-TYPE
        SYNTAX          DisplayString(SIZE(0..255))
        MAX-ACCESS      read-write
        STATUS          current
        DESCRIPTION
            "SNMP trap IP address or host name (host 3)"
        ::= { snmpAgent 9 }

    snmpAgentTrapPort3 OBJECT-TYPE
        SYNTAX          Integer32(0..65535)
        MAX-ACCESS      read-write
        STATUS          current
        DESCRIPTION
            "SNMP trap port (host 3) "
        ::= { snmpAgent 10 }

    snmpAgentTrapHost4 OBJECT-TYPE
        SYNTAX          DisplayString(SIZE(0..255))
        MAX-ACCESS      read-write
        STATUS          current
        DESCRIPTION
            "SNMP trap IP address or host name (host 4)"
        ::= { snmpAgent 11 }

    snmpAgentTrapPort4 OBJECT-TYPE
        SYNTAX          Integer32(0..65535)
        MAX-ACCESS      read-write
        STATUS          current
        DESCRIPTION
            "SNMP trap port (host 4)"
        ::= { snmpAgent 12 }

    snmpAgentV3Enable OBJECT-TYPE
        SYNTAX          INTEGER { disable(0), enable(1) }
        MAX-ACCESS      read-write
        STATUS          current
        DESCRIPTION
            "Enable or disable SNMPv3"
        ::= { snmpAgent 13 }

    snmpAgentV3AuthType OBJECT-TYPE
        SYNTAX          INTEGER { md5(0), sha(1) }
        MAX-ACCESS      read-write
        STATUS          current
        DESCRIPTION
            "SNMPv3 authentication type"
        ::= { snmpAgent 14 }

    snmpAgentV3PrivProtocol OBJECT-TYPE
        SYNTAX          INTEGER { des(0), aes(1) }
        MAX-ACCESS      read-write
        STATUS          current
        DESCRIPTION
            "SNMPv3 privacy protocol"
        ::= { snmpAgent 15 }

    snmpAgentV3ReadWriteUser OBJECT-TYPE
        SYNTAX          DisplayString(SIZE(0..30))
        MAX-ACCESS      read-write
        STATUS          current
        DESCRIPTION
            "SNMPv3 read-write user"
        ::= { snmpAgent 16 }

    snmpAgentV3ReadWriteUserAuthPassphrase OBJECT-TYPE
        SYNTAX          DisplayString(SIZE(8..30))
        MAX-ACCESS      read-write
        STATUS          current
        DESCRIPTION
            "SNMPv3 read-write user authentication passphrase"
        ::= { snmpAgent 17 }

    snmpAgentV3ReadWriteUserAuthPassphraseEnc OBJECT-TYPE
        SYNTAX          DisplayString(SIZE(16..60))
        MAX-ACCESS      read-write
        STATUS          current
        DESCRIPTION
            "SNMPv3 read-write user authentication passphrase (encrypted)"
        ::= { snmpAgent 18 }

    snmpAgentV3ReadWriteUserPrivPassphrase OBJECT-TYPE
        SYNTAX          DisplayString(SIZE(8..30))
        MAX-ACCESS      read-write
        STATUS          current
        DESCRIPTION
            "SNMPv3 read-write user privacy passphrase"
        ::= { snmpAgent 19 }

    snmpAgentV3ReadWriteUserPrivPassphraseEnc OBJECT-TYPE
        SYNTAX          DisplayString(SIZE(16..60))
        MAX-ACCESS      read-write
        STATUS          current
        DESCRIPTION
            "SNMPv3 read-write user privacy passphrase (encrypted)"
        ::= { snmpAgent 20 }

    snmpAgentV3ReadOnlyUser OBJECT-TYPE
        SYNTAX          DisplayString(SIZE(0..30))
        MAX-ACCESS      read-write
        STATUS          current
        DESCRIPTION
            "SNMPv3 read-only user"
        ::= { snmpAgent 21 }

    snmpAgentV3ReadOnlyUserAuthPassphrase OBJECT-TYPE
        SYNTAX          DisplayString(SIZE(8..30))
        MAX-ACCESS      read-write
        STATUS          current
        DESCRIPTION
            "SNMPv3 read-only user authentication passphrase"
        ::= { snmpAgent 22 }

    snmpAgentV3ReadOnlyUserAuthPassphraseEnc OBJECT-TYPE
        SYNTAX          DisplayString(SIZE(16..60))
        MAX-ACCESS      read-write
        STATUS          current
        DESCRIPTION
            "SNMPv3 read-only user authentication passphrase (encrypted)"
        ::= { snmpAgent 23 }

    snmpAgentV3ReadOnlyUserPrivPassphrase OBJECT-TYPE
        SYNTAX          DisplayString(SIZE(8..30))
        MAX-ACCESS      read-write
        STATUS          current
        DESCRIPTION
            "SNMPv3 read-only user privacy passphrase"
        ::= { snmpAgent 24 }

    snmpAgentV3ReadOnlyUserPrivPassphraseEnc OBJECT-TYPE
        SYNTAX          DisplayString(SIZE(16..60))
        MAX-ACCESS      read-write
        STATUS          current
        DESCRIPTION
            "SNMPv3 read-only user privacy passphrase (encrypted)"
        ::= { snmpAgent 25 }

    snmpAgentEngineID OBJECT-TYPE
        SYNTAX          DisplayString(SIZE(24..50))
        MAX-ACCESS      read-write
        STATUS          current
        DESCRIPTION
            "SNMP agent engine ID (in hex)"
        ::= { snmpAgent 26 }

    snmpAgentRestart OBJECT-TYPE
        SYNTAX          INTEGER { restart(1) }
        MAX-ACCESS      read-write
        STATUS          current
        DESCRIPTION
            "Restart SNMP agent"
        ::= { snmpAgent 27 }

    snmpAgentKeepAlive OBJECT-TYPE
        SYNTAX          Integer32(0..999)
        MAX-ACCESS      read-write
        STATUS          current
        DESCRIPTION
            "SNMP trap keepalive time (in minutes)"
        ::= { snmpAgent 28 }

    snmpAgentReadWriteCommunityEnc OBJECT-TYPE
        SYNTAX          DisplayString(SIZE(0..100))
        MAX-ACCESS      read-write
        STATUS          current
        DESCRIPTION
            "SNMP read-write community string (encrypted)"
        ::= { snmpAgent 29 }

    snmpAgentReadOnlyCommunityEnc OBJECT-TYPE
        SYNTAX          DisplayString(SIZE(0..100))
        MAX-ACCESS      read-write
        STATUS          current
        DESCRIPTION
            "SNMP read-only community string (encrypted)"
        ::= { snmpAgent 30 }

--
-- SSID
--

    ssidTable OBJECT-TYPE
        SYNTAX          SEQUENCE OF SsidEntry
        MAX-ACCESS      not-accessible
        STATUS          current
        DESCRIPTION
            "SSID table for the Array"
        ::= { ssid 1 }

    ssidEntry OBJECT-TYPE
        SYNTAX          SsidEntry
        MAX-ACCESS      not-accessible
        STATUS          current
        DESCRIPTION
            "SSID table entry"
        INDEX       { ssidIndex }
        ::= { ssidTable 1 }

    SsidEntry ::= SEQUENCE {
        ssidIndex                           Integer32,
        ssidName                            DisplayString,
        ssidBroadcast                       INTEGER,
        ssidBand                            INTEGER,
        ssidQOS                             Integer32,
        ssidVlan                            Integer32,
        ssidDhcpPool                        DisplayString,
        ssidEncryption                      INTEGER,
        ssidDefaultSecurity                 INTEGER,
        ssidWepDefaultKeyID                 Integer32,
        ssidWepKey1Size                     INTEGER,
        ssidWepKey1String                   DisplayString,
        ssidWepKey2Size                     INTEGER,
        ssidWepKey2String                   DisplayString,
        ssidWepKey3Size                     INTEGER,
        ssidWepKey3String                   DisplayString,
        ssidWepKey4Size                     INTEGER,
        ssidWepKey4String                   DisplayString,
        ssidWpaEAP                          INTEGER,
        ssidWpaPSK                          INTEGER,
        ssidWpaPassphrase                   DisplayString,
        ssidRadiusEnable                    INTEGER,
        ssidRadiusPriServerIPAddress        IpAddress,
        ssidRadiusPriServerPort             Integer32,
        ssidRadiusPriServerSecret           DisplayString,
        ssidRadiusSecServerIPAddress        IpAddress,
        ssidRadiusSecServerPort             Integer32,
        ssidRadiusSecServerSecret           DisplayString,
        ssidRadiusTimeout                   Integer32,
        ssidRadiusAcctEnable                INTEGER,
        ssidRadiusAcctPriServerIPAddress    IpAddress,
        ssidRadiusAcctPriServerPort         Integer32,
        ssidRadiusAcctPriServerSecret       DisplayString,
        ssidRadiusAcctSecServerIPAddress    IpAddress,
        ssidRadiusAcctSecServerPort         Integer32,
        ssidRadiusAcctSecServerSecret       DisplayString,
        ssidRadiusAcctInterval              Integer32,
        ssidAuthentication                  INTEGER,
        ssidRowStatus                       RowStatus,
        ssidRoamingLayer                    INTEGER,
        ssidRadiusPriServerHostname         DisplayString,
        ssidRadiusSecServerHostname         DisplayString,
        ssidRadiusAcctPriServerHostname     DisplayString,
        ssidRadiusAcctSecServerHostname     DisplayString,
        ssidWepKey1StringForm               INTEGER,
        ssidWepKey2StringForm               INTEGER,
        ssidWepKey3StringForm               INTEGER,
        ssidWepKey4StringForm               INTEGER,
        ssidWpaPassphraseForm               INTEGER,
        ssidRadiusPriServerSecretForm       INTEGER,
        ssidRadiusSecServerSecretForm       INTEGER,
        ssidRadiusAcctPriServerSecretForm   INTEGER,
        ssidRadiusAcctSecServerSecretForm   INTEGER,
        ssidFilterList                      DisplayString,
        ssidWpaTKIP                         INTEGER,
        ssidWpaAES                          INTEGER,
        ssidActiveIAPs                      Integer32,
        ssidAclEnable                       INTEGER,
        ssidFallback                        INTEGER,
        ssidTunnel                          DisplayString,
        ssidMdmAuth                         INTEGER,
        ssidDhcpOption                      INTEGER,
        ssidWpaUPSKCacheTimeout             Integer32,
        ssidWpaUPSKServerConnError          INTEGER,
        ssidVlanPool                        DisplayString,
        ssidExpiration                      Integer32,
        ssidDateOn                          Integer32,
        ssidDateOff                         Integer32,
        ssidRadiusFailoverTimeout           Integer32,
        ssidDot11rEnable                       INTEGER
    }

    ssidIndex OBJECT-TYPE
        SYNTAX          Integer32
        MAX-ACCESS      not-accessible
        STATUS          current
        DESCRIPTION
            "SSID table index"
        ::= { ssidEntry 1 }

    ssidName OBJECT-TYPE
        SYNTAX          DisplayString(SIZE(1..32))
        MAX-ACCESS      read-create
        STATUS          current
        DESCRIPTION
            "SSID name"
        ::= { ssidEntry 2 }

    ssidBroadcast OBJECT-TYPE
        SYNTAX          INTEGER { disable(0), enable(1) }
        MAX-ACCESS      read-create
        STATUS          current
        DESCRIPTION
            "Enable/disable SSID broadcast"
        ::= { ssidEntry 3 }

    ssidBand OBJECT-TYPE
        SYNTAX          INTEGER { both(1), dot11a(2),  dot11bg(3) }
        MAX-ACCESS      read-create
        STATUS          current
        DESCRIPTION
            "SSID 802.11 band"
        ::= { ssidEntry 4 }

    ssidQOS OBJECT-TYPE
        SYNTAX          Integer32(0..3)
        MAX-ACCESS      read-create
        STATUS          current
        DESCRIPTION
            "SSID QoS level"
        ::= { ssidEntry 5 }

    ssidVlan OBJECT-TYPE
        SYNTAX          Integer32(0..4095)
        MAX-ACCESS      read-create
        STATUS          current
        DESCRIPTION
            "SSID vlan ID"
        ::= { ssidEntry 6 }

    ssidDhcpPool OBJECT-TYPE
        SYNTAX          DisplayString(SIZE(0..20))
        MAX-ACCESS      read-create
        STATUS          current
        DESCRIPTION
            "SSID DHCP pool"
        ::= { ssidEntry 7 }

    ssidEncryption OBJECT-TYPE
        SYNTAX          INTEGER { none(0), wep(1), wpa(2), wpa2(3), wpa-both(4) }
        MAX-ACCESS      read-create
        STATUS          current
        DESCRIPTION
            "SSID encryption type"
        ::= { ssidEntry 8 }

    ssidDefaultSecurity OBJECT-TYPE
        SYNTAX          INTEGER { disable(0), enable(1) }
        MAX-ACCESS      read-create
        STATUS          current
        DESCRIPTION
            "Use default security settings"
        ::= { ssidEntry 9 }

    ssidWepDefaultKeyID OBJECT-TYPE
        SYNTAX          Integer32(1..4)
        MAX-ACCESS      read-create
        STATUS          current
        DESCRIPTION
            "Default encryption key id for WEP"
        ::= { ssidEntry 10 }

    ssidWepKey1Size OBJECT-TYPE
        SYNTAX          INTEGER{ wep40(1), wep128(2) }
        MAX-ACCESS      read-only
        STATUS          current
        DESCRIPTION
            "WEP key 1 size - 40 or 128 bits"
        ::= { ssidEntry 11 }

    ssidWepKey1String OBJECT-TYPE
        SYNTAX          DisplayString(SIZE(0..26))
        MAX-ACCESS      read-create
        STATUS          current
        DESCRIPTION
            "WEP encryption key 1"
        ::= { ssidEntry 12 }

    ssidWepKey2Size OBJECT-TYPE
        SYNTAX          INTEGER{ wep40(1), wep128(2) }
        MAX-ACCESS      read-only
        STATUS          current
        DESCRIPTION
            "WEP key 2 size - 40 or 128 bits"
        ::= { ssidEntry 13 }

    ssidWepKey2String OBJECT-TYPE
        SYNTAX          DisplayString(SIZE(0..26))
        MAX-ACCESS      read-create
        STATUS          current
        DESCRIPTION
            "WEP encryption key 2"
        ::= { ssidEntry 14 }

    ssidWepKey3Size OBJECT-TYPE
        SYNTAX          INTEGER{ wep40(1), wep128(2) }
        MAX-ACCESS      read-only
        STATUS          current
        DESCRIPTION
            "WEP key 3 size - 40 or 128 bits"
        ::= { ssidEntry 15 }

    ssidWepKey3String OBJECT-TYPE
        SYNTAX          DisplayString(SIZE(0..26))
        MAX-ACCESS      read-create
        STATUS          current
        DESCRIPTION
            "WEP encryption key 3"
        ::= { ssidEntry 16 }

    ssidWepKey4Size OBJECT-TYPE
        SYNTAX          INTEGER{ wep40(1), wep128(2) }
        MAX-ACCESS      read-only
        STATUS          current
        DESCRIPTION
            "WEP key 4 size - 40 or 128 bits"
        ::= { ssidEntry 17 }

    ssidWepKey4String OBJECT-TYPE
        SYNTAX          DisplayString(SIZE(0..26))
        MAX-ACCESS      read-create
        STATUS          current
        DESCRIPTION
            "WEP encryption key 4"
        ::= { ssidEntry 18 }

    ssidWpaEAP OBJECT-TYPE
        SYNTAX          INTEGER { disable(0), enable(1) }
        MAX-ACCESS      read-create
        STATUS          current
        DESCRIPTION
            "EAP enable or disable"
        ::= { ssidEntry 19 }

    ssidWpaPSK OBJECT-TYPE
        SYNTAX          INTEGER { disable(0), enable(1), u-psk(2) }
        MAX-ACCESS      read-create
        STATUS          current
        DESCRIPTION
            "PSK enable, disable or U-PSK"
        ::= { ssidEntry 20 }

    ssidWpaPassphrase OBJECT-TYPE
        SYNTAX          DisplayString(SIZE(0|8..128))
        MAX-ACCESS      read-create
        STATUS          current
        DESCRIPTION
            "PSK ASCII passphrase or Hex key"
        ::= { ssidEntry 21 }

    ssidRadiusEnable OBJECT-TYPE
        SYNTAX          INTEGER { external(1), internal(2), active-directory(3) }
        MAX-ACCESS      read-create
        STATUS          current
        DESCRIPTION
            "Radius server enabled"
        ::= { ssidEntry 22 }

    ssidRadiusPriServerIPAddress OBJECT-TYPE
        SYNTAX          IpAddress
        MAX-ACCESS      read-create
        STATUS          current
        DESCRIPTION
            "Primary Radius server IP address"
        ::= { ssidEntry 23 }

    ssidRadiusPriServerPort OBJECT-TYPE
        SYNTAX          Integer32(0..65535)
        MAX-ACCESS      read-create
        STATUS          current
        DESCRIPTION
            "Primary Radius server port"
        ::= { ssidEntry 24 }

    ssidRadiusPriServerSecret OBJECT-TYPE
        SYNTAX          DisplayString(SIZE(0..128))
        MAX-ACCESS      read-create
        STATUS          current
        DESCRIPTION
            "Primary Radius server secret"
        ::= { ssidEntry 25 }

    ssidRadiusSecServerIPAddress OBJECT-TYPE
        SYNTAX          IpAddress
        MAX-ACCESS      read-create
        STATUS          current
        DESCRIPTION
            "Secondary Radius server IP address"
        ::= { ssidEntry 26 }

    ssidRadiusSecServerPort OBJECT-TYPE
        SYNTAX          Integer32(0..65535)
        MAX-ACCESS      read-create
        STATUS          current
        DESCRIPTION
            "Secondary Radius server port"
        ::= { ssidEntry 27 }

    ssidRadiusSecServerSecret OBJECT-TYPE
        SYNTAX          DisplayString(SIZE(0..128))
        MAX-ACCESS      read-create
        STATUS          current
        DESCRIPTION
            "Secondary Radius server secret"
        ::= { ssidEntry 28 }

    ssidRadiusTimeout OBJECT-TYPE
        SYNTAX          Integer32(0..65535)
        MAX-ACCESS      read-create
        STATUS          current
        DESCRIPTION
            "Timeout until the primary server is retired _ given up on"
        ::= { ssidEntry 29 }

    ssidRadiusAcctEnable OBJECT-TYPE
        SYNTAX          INTEGER { disable(0), enable(1) }
        MAX-ACCESS      read-create
        STATUS          current
        DESCRIPTION
            "Enable or disable Radius Accounting"
        ::= { ssidEntry 30 }

    ssidRadiusAcctPriServerIPAddress OBJECT-TYPE
        SYNTAX          IpAddress
        MAX-ACCESS      read-create
        STATUS          current
        DESCRIPTION
            "Primary Radius Accounting server IP address"
        ::= { ssidEntry 31 }

    ssidRadiusAcctPriServerPort OBJECT-TYPE
        SYNTAX          Integer32(0..65535)
        MAX-ACCESS      read-create
        STATUS          current
        DESCRIPTION
            "Primary Radius Accounting server port"
        ::= { ssidEntry 32 }

    ssidRadiusAcctPriServerSecret OBJECT-TYPE
        SYNTAX          DisplayString(SIZE(0..128))
        MAX-ACCESS      read-create
        STATUS          current
        DESCRIPTION
            "Primary Radius Accounting server secret"
        ::= { ssidEntry 33 }

    ssidRadiusAcctSecServerIPAddress OBJECT-TYPE
        SYNTAX          IpAddress
        MAX-ACCESS      read-create
        STATUS          current
        DESCRIPTION
            "Secondary Radius Accounting server IP address"
        ::= { ssidEntry 34 }

    ssidRadiusAcctSecServerPort OBJECT-TYPE
        SYNTAX          Integer32(0..65535)
        MAX-ACCESS      read-create
        STATUS          current
        DESCRIPTION
            "Secondary Radius Accounting server port"
        ::= { ssidEntry 35 }

    ssidRadiusAcctSecServerSecret OBJECT-TYPE
        SYNTAX          DisplayString(SIZE(0..128))
        MAX-ACCESS      read-create
        STATUS          current
        DESCRIPTION
            "Secondary Radius Accounting server secret"
        ::= { ssidEntry 36}

    ssidRadiusAcctInterval OBJECT-TYPE
        SYNTAX          Integer32(60..65535)
        MAX-ACCESS      read-create
        STATUS          current
        DESCRIPTION
            "Interim accounting update interval"
        ::= { ssidEntry 37 }

    ssidAuthentication OBJECT-TYPE
        SYNTAX          INTEGER { open(0), radius-mac(1), dot1x(2) }
        MAX-ACCESS      read-create
        STATUS          current
        DESCRIPTION
            "SSID authentication type"
        ::= { ssidEntry 38 }

    ssidRowStatus OBJECT-TYPE
        SYNTAX          RowStatus
        MAX-ACCESS      read-create
        STATUS          current
        DESCRIPTION
            "Status of the SSID row entry"
        ::= { ssidEntry 39 }

    ssidRoamingLayer OBJECT-TYPE
        SYNTAX          INTEGER { layer-2-only(0), layer-2-and-3(1), none(2) }
        MAX-ACCESS      read-create
        STATUS          current
        DESCRIPTION
            "Fast roaming layer allowed for this SSID"
        ::= { ssidEntry 40 }

    ssidRadiusPriServerHostname OBJECT-TYPE
        SYNTAX          DisplayString(SIZE(0.. 255))
        MAX-ACCESS      read-create
        STATUS          current
        DESCRIPTION
            "Primary Radius server hostname"
        ::= { ssidEntry 41 }

    ssidRadiusSecServerHostname OBJECT-TYPE
        SYNTAX          DisplayString(SIZE(0.. 255))
        MAX-ACCESS      read-create
        STATUS          current
        DESCRIPTION
            "Secondary Radius server hostname"
        ::= { ssidEntry 42 }

    ssidRadiusAcctPriServerHostname OBJECT-TYPE
        SYNTAX          DisplayString(SIZE(0.. 255))
        MAX-ACCESS      read-create
        STATUS          current
        DESCRIPTION
            "Primary Radius Accounting server hostname"
        ::= { ssidEntry 43 }

    ssidRadiusAcctSecServerHostname OBJECT-TYPE
        SYNTAX          DisplayString(SIZE(0.. 255))
        MAX-ACCESS      read-create
        STATUS          current
        DESCRIPTION
            "Secondary Radius Accounting server hostname"
        ::= { ssidEntry 44 }

    ssidWepKey1StringForm OBJECT-TYPE
        SYNTAX          INTEGER { clear(0), encrypted(1) }
        MAX-ACCESS      read-create
        STATUS          current
        DESCRIPTION
            "WEP key 1 string form"
        ::= { ssidEntry 45 }

    ssidWepKey2StringForm OBJECT-TYPE
        SYNTAX          INTEGER { clear(0), encrypted(1) }
        MAX-ACCESS      read-create
        STATUS          current
        DESCRIPTION
            "WEP key 2 string form"
        ::= { ssidEntry 46 }

    ssidWepKey3StringForm OBJECT-TYPE
        SYNTAX          INTEGER { clear(0), encrypted(1) }
        MAX-ACCESS      read-create
        STATUS          current
        DESCRIPTION
            "WEP key 3 string form"
        ::= { ssidEntry 47 }

    ssidWepKey4StringForm OBJECT-TYPE
        SYNTAX          INTEGER { clear(0), encrypted(1) }
        MAX-ACCESS      read-create
        STATUS          current
        DESCRIPTION
            "WEP key 4 string form"
        ::= { ssidEntry 48 }

    ssidWpaPassphraseForm OBJECT-TYPE
        SYNTAX          INTEGER { clear(0), encrypted(1) }
        MAX-ACCESS      read-create
        STATUS          current
        DESCRIPTION
            "PSK passphrase form"
        ::= { ssidEntry 49 }

   ssidRadiusPriServerSecretForm OBJECT-TYPE
        SYNTAX          INTEGER { clear(0), encrypted(1) }
        MAX-ACCESS      read-create
        STATUS          current
        DESCRIPTION
            "Primary Radius server secret form"
        ::= { ssidEntry 50 }

    ssidRadiusSecServerSecretForm OBJECT-TYPE
        SYNTAX          INTEGER { clear(0), encrypted(1) }
        MAX-ACCESS      read-create
        STATUS          current
        DESCRIPTION
            "Secondary Radius server secret form"
        ::= { ssidEntry 51 }

    ssidRadiusAcctPriServerSecretForm OBJECT-TYPE
        SYNTAX          INTEGER { clear(0), encrypted(1) }
        MAX-ACCESS      read-create
        STATUS          current
        DESCRIPTION
            "Primary Radius Accounting server secret form"
        ::= { ssidEntry 52 }

    ssidRadiusAcctSecServerSecretForm OBJECT-TYPE
        SYNTAX          INTEGER { clear(0), encrypted(1) }
        MAX-ACCESS      read-create
        STATUS          current
        DESCRIPTION
            "Secondary Radius Accounting server secret form"
        ::= { ssidEntry 53 }

    ssidFilterList OBJECT-TYPE
        SYNTAX          DisplayString(SIZE(0..20))
        MAX-ACCESS      read-create
        STATUS          current
        DESCRIPTION
            "SSID filter list"
        ::= { ssidEntry 54 }

    ssidWpaTKIP OBJECT-TYPE
        SYNTAX          INTEGER { disable(0), enable(1) }
        MAX-ACCESS      read-create
        STATUS          current
        DESCRIPTION
            "TKIP enable or disable"
        ::= { ssidEntry 55 }

    ssidWpaAES OBJECT-TYPE
        SYNTAX          INTEGER { disable(0), enable(1) }
        MAX-ACCESS      read-create
        STATUS          current
        DESCRIPTION
            "AES enable or disable"
        ::= { ssidEntry 56 }

    ssidActiveIAPs OBJECT-TYPE
        SYNTAX          Integer32(0..65535)
        MAX-ACCESS      read-create
        STATUS          current
        DESCRIPTION
            "Define active IAPs for this SSID"
        ::= { ssidEntry 57 }

    ssidAclEnable OBJECT-TYPE
        SYNTAX          INTEGER { disable(0), allow(1) , deny(2), deny-include-blocked-rogues(3) }
        MAX-ACCESS      read-create
        STATUS          current
        DESCRIPTION
            "SSID access control list enable/disable"
        ::= { ssidEntry 58 }

    ssidFallback OBJECT-TYPE
        SYNTAX          INTEGER { none(0), disable-ssid(1) }
        MAX-ACCESS      read-create
        STATUS          current
        DESCRIPTION
            "Define network connectivity fallback mode for this SSID"
        ::= { ssidEntry 59 }

    ssidTunnel OBJECT-TYPE
        SYNTAX          DisplayString(SIZE(0..20))
        MAX-ACCESS      read-create
        STATUS          current
        DESCRIPTION
            "Specify tunnel for bridging SSID data traffic"
        ::= { ssidEntry 60 }

    ssidMdmAuth OBJECT-TYPE
        SYNTAX          INTEGER { none(0), airwatch(1) }
        MAX-ACCESS      read-create
        STATUS          current
        DESCRIPTION
            "MDM authentication type used by this SSID"
        ::= { ssidEntry 61 }

    ssidDhcpOption OBJECT-TYPE
        SYNTAX          INTEGER { disable(0), enable(1) }
        MAX-ACCESS      read-create
        STATUS          current
        DESCRIPTION
            "Enable or disable insertion of relay agent information option in station DHCP requests"
        ::= { ssidEntry 62 }

    ssidWpaUPSKCacheTimeout OBJECT-TYPE
        SYNTAX          Integer32(0..10080)
        MAX-ACCESS      read-create
        STATUS          current
        DESCRIPTION
            "U-PSK cache timeout (in minutes)"
        ::= { ssidEntry 63 }

    ssidWpaUPSKServerConnError OBJECT-TYPE
        SYNTAX          INTEGER { block(0), allow(1) }
        MAX-ACCESS      read-create
        STATUS          current
        DESCRIPTION
            "U-PSK server connection error action"
        ::= { ssidEntry 64 }

    ssidVlanPool OBJECT-TYPE
        SYNTAX          DisplayString(SIZE(0..20))
        MAX-ACCESS      read-create
        STATUS          current
        DESCRIPTION
            "SSID VLAN pool"
        ::= { ssidEntry 65 }

    ssidExpiration OBJECT-TYPE
        SYNTAX          Integer32
        MAX-ACCESS      read-create
        STATUS          current
        DESCRIPTION
            "SSID Expiration"
        ::= { ssidEntry 66 }

    ssidDateOn OBJECT-TYPE
        SYNTAX          Integer32
        MAX-ACCESS      read-create
        STATUS          current
        DESCRIPTION
            "SSID Scheduling Date On"
        ::= { ssidEntry 67 }

    ssidDateOff OBJECT-TYPE
        SYNTAX          Integer32
        MAX-ACCESS      read-create
        STATUS          current
        DESCRIPTION
            "SSID Scheduling Date Off"
        ::= { ssidEntry 68 }

    ssidRadiusFailoverTimeout OBJECT-TYPE
        SYNTAX          Integer32(10..600)
        MAX-ACCESS      read-create
        STATUS          current
        DESCRIPTION
            "Timeout before failover to another server after current server failed"
        ::= { ssidEntry 69 }

    ssidDot11rEnable OBJECT-TYPE
        SYNTAX          INTEGER { disable(0), enable(1) }
        MAX-ACCESS      read-create
        STATUS          current
        DESCRIPTION
            "Enable/disable support for 802.11r beacons"
        ::= { ssidEntry 70 }

    ssidTableReset OBJECT-TYPE
        SYNTAX          INTEGER { reset(1) }
        MAX-ACCESS      read-write
        STATUS          current
        DESCRIPTION
            "Reset SSID table (clear all entries and restore default)"
        ::= { ssid 2 }

    ssidTableClear OBJECT-TYPE
        SYNTAX          INTEGER { clear(1) }
        MAX-ACCESS      read-write
        STATUS          current
        DESCRIPTION
            "Clear all entries in SSID table"
        ::= { ssid 3 }

    ssidLimitsTable OBJECT-TYPE
        SYNTAX          SEQUENCE OF SsidLimitsEntry
        MAX-ACCESS      not-accessible
        STATUS          current
        DESCRIPTION
            "SSID limits table for the Array"
        ::= { ssid 4 }

    ssidLimitsEntry OBJECT-TYPE
        SYNTAX          SsidLimitsEntry
        MAX-ACCESS      not-accessible
        STATUS          current
        DESCRIPTION
            "SSID limits table entry"
        INDEX       { ssidLimitsIndex }
        ::= { ssidLimitsTable 1 }

    SsidLimitsEntry ::= SEQUENCE {
        ssidLimitsIndex                 Integer32,
        ssidLimitsSsidName              DisplayString,
        ssidLimitsEnable                INTEGER,
        ssidLimitsTrafficLimit          Integer32,
        ssidLimitsTrafficLimitSta       Integer32,
        ssidLimitsTimeOn                Integer32,
        ssidLimitsTimeOff               Integer32,
        ssidLimitsDaysOnMon             INTEGER,
        ssidLimitsDaysOnTue             INTEGER,
        ssidLimitsDaysOnWed             INTEGER,
        ssidLimitsDaysOnThu             INTEGER,
        ssidLimitsDaysOnFri             INTEGER,
        ssidLimitsDaysOnSat             INTEGER,
        ssidLimitsDaysOnSun             INTEGER,
        ssidLimitsActive                INTEGER,
        ssidLimitsStationLimit          Integer32,
        ssidLimitsTrafficLimitKbps      Integer32,
        ssidLimitsTrafficLimitKbpsSta   Integer32
    }

    ssidLimitsIndex OBJECT-TYPE
        SYNTAX          Integer32
        MAX-ACCESS      not-accessible
        STATUS          current
        DESCRIPTION
            "SSID limits table index"
        ::= { ssidLimitsEntry 1 }

    ssidLimitsSsidName OBJECT-TYPE
        SYNTAX          DisplayString
        MAX-ACCESS      read-only
        STATUS          current
        DESCRIPTION
            "SSID name"
        ::= { ssidLimitsEntry 2 }

    ssidLimitsEnable OBJECT-TYPE
        SYNTAX          INTEGER { disable(0), enable(1) }
        MAX-ACCESS      read-write
        STATUS          current
        DESCRIPTION
            "Enable or disable SSID"
        ::= { ssidLimitsEntry 3 }

    ssidLimitsTrafficLimit OBJECT-TYPE
        SYNTAX          Integer32(0..1000000)
        MAX-ACCESS      read-write
        STATUS          current
        DESCRIPTION
            "Traffic limit for SSID (10 to 1000000 pps, 0 - unlimited)"
        ::= { ssidLimitsEntry 4 }

    ssidLimitsTrafficLimitSta OBJECT-TYPE
        SYNTAX          Integer32(0..100000)
        MAX-ACCESS      read-write
        STATUS          current
        DESCRIPTION
            "Traffic limit per station for SSID (10 to 100000 pps, 0 - unlimited)"
        ::= { ssidLimitsEntry 5 }

    ssidLimitsTimeOn OBJECT-TYPE
        SYNTAX          Integer32(-1..1439)
        MAX-ACCESS      read-write
        STATUS          current
        DESCRIPTION
            "Set daily time SSID is active (in minutes, -1 - always)"
        ::= { ssidLimitsEntry 6 }

    ssidLimitsTimeOff OBJECT-TYPE
        SYNTAX          Integer32(-1..1439)
        MAX-ACCESS      read-write
        STATUS          current
        DESCRIPTION
            "Set daily time SSID is inactive (in minutes, -1 - never)"
        ::= { ssidLimitsEntry 7 }

    ssidLimitsDaysOnMon OBJECT-TYPE
        SYNTAX          INTEGER { off(0), on(1) }
        MAX-ACCESS      read-write
        STATUS          current
        DESCRIPTION
            "SSID is on/off on Monday"
        ::= { ssidLimitsEntry 8 }

    ssidLimitsDaysOnTue OBJECT-TYPE
        SYNTAX          INTEGER { off(0), on(1) }
        MAX-ACCESS      read-write
        STATUS          current
        DESCRIPTION
            "SSID is on/off on Tuesday"
        ::= { ssidLimitsEntry 9 }

    ssidLimitsDaysOnWed OBJECT-TYPE
        SYNTAX          INTEGER { off(0), on(1) }
        MAX-ACCESS      read-write
        STATUS          current
        DESCRIPTION
            "SSID is on/off on Wednesday"
        ::= { ssidLimitsEntry 10 }

    ssidLimitsDaysOnThu OBJECT-TYPE
        SYNTAX          INTEGER { off(0), on(1) }
        MAX-ACCESS      read-write
        STATUS          current
        DESCRIPTION
            "SSID is on/off on Thursday"
        ::= { ssidLimitsEntry 11 }

    ssidLimitsDaysOnFri OBJECT-TYPE
        SYNTAX          INTEGER { off(0), on(1) }
        MAX-ACCESS      read-write
        STATUS          current
        DESCRIPTION
            "SSID is on/off on Friday"
        ::= { ssidLimitsEntry 12 }

    ssidLimitsDaysOnSat OBJECT-TYPE
        SYNTAX          INTEGER { off(0), on(1) }
        MAX-ACCESS      read-write
        STATUS          current
        DESCRIPTION
            "SSID is on/off on Saturday"
        ::= { ssidLimitsEntry 13 }

    ssidLimitsDaysOnSun OBJECT-TYPE
        SYNTAX          INTEGER { off(0), on(1) }
        MAX-ACCESS      read-write
        STATUS          current
        DESCRIPTION
            "SSID is on/off on Sunday"
        ::= { ssidLimitsEntry 14 }

    ssidLimitsActive OBJECT-TYPE
        SYNTAX          INTEGER { inactive(0), active(1) }
        MAX-ACCESS      read-only
        STATUS          current
        DESCRIPTION
            "Flag indicating whether SSID is currently active"
        ::= { ssidLimitsEntry 15 }

    ssidLimitsStationLimit OBJECT-TYPE
        SYNTAX          Integer32(1..3840)
        MAX-ACCESS      read-write
        STATUS          current
        DESCRIPTION
            "Station limit for SSID"
        ::= { ssidLimitsEntry 16 }

    ssidLimitsTrafficLimitKbps OBJECT-TYPE
        SYNTAX          Integer32(0..4000000)
        MAX-ACCESS      read-write
        STATUS          current
        DESCRIPTION
            "Traffic limit for SSID (10 to 4000000 kbps, 0 - unlimited)"
        ::= { ssidLimitsEntry 17 }

    ssidLimitsTrafficLimitKbpsSta OBJECT-TYPE
        SYNTAX          Integer32(0..400000)
        MAX-ACCESS      read-write
        STATUS          current
        DESCRIPTION
            "Traffic limit per station for SSID (10 to 400000 kbps, 0 - unlimited)"
        ::= { ssidLimitsEntry 18 }

    ssidWprTable OBJECT-TYPE
        SYNTAX          SEQUENCE OF SsidWprEntry
        MAX-ACCESS      not-accessible
        STATUS          current
        DESCRIPTION
            "SSID Web Page Redirect (WPR) table for the Array"
        ::= { ssid 5 }

    ssidWprEntry OBJECT-TYPE
        SYNTAX          SsidWprEntry
        MAX-ACCESS      not-accessible
        STATUS          current
        DESCRIPTION
            "SSID WPR table entry"
        INDEX       { ssidWprIndex }
        ::= { ssidWprTable 1 }

    SsidWprEntry ::= SEQUENCE {
        ssidWprIndex                Integer32,
        ssidWprSsidName             DisplayString,
        ssidWprEnable               INTEGER,
        ssidWprServerType           INTEGER,
        ssidWprUrl                  DisplayString,
        ssidWprSharedSecret         DisplayString,
        ssidWprScreenType           INTEGER,
        ssidWprScreenTimeout        Integer32,
        ssidWprLandingPage          DisplayString,
        ssidWprSharedSecretForm     INTEGER,
        ssidWprAuthType             INTEGER,
        ssidWprHttpsEnable          INTEGER,
        ssidWprBackground           DisplayString,
        ssidWprLogoImage            DisplayString,
        ssidWprHeaderText           DisplayString,
        ssidWprFooterText           DisplayString,
        ssidWprAuthTimeout          Integer32,
        ssidWprHttpsPassthru        INTEGER
    }

    ssidWprIndex OBJECT-TYPE
        SYNTAX          Integer32
        MAX-ACCESS      not-accessible
        STATUS          current
        DESCRIPTION
            "SSID WPR table index"
        ::= { ssidWprEntry 1 }

    ssidWprSsidName OBJECT-TYPE
        SYNTAX          DisplayString
        MAX-ACCESS      read-only
        STATUS          current
        DESCRIPTION
            "SSID name"
        ::= { ssidWprEntry 2 }

    ssidWprEnable OBJECT-TYPE
        SYNTAX          INTEGER { disable(0), enable(1) }
        MAX-ACCESS      read-write
        STATUS          current
        DESCRIPTION
            "Enable or disable WPR for SSID"
        ::= { ssidWprEntry 3 }

    ssidWprServerType OBJECT-TYPE
        SYNTAX          INTEGER { external(0), internal(1), cloud(2) }
        MAX-ACCESS      read-write
        STATUS          current
        DESCRIPTION
            "Server type for WPR"
        ::= { ssidWprEntry 6 }

    ssidWprUrl OBJECT-TYPE
        SYNTAX          DisplayString(SIZE(0..255))
        MAX-ACCESS      read-write
        STATUS          current
        DESCRIPTION
            "URL for WPR"
        ::= { ssidWprEntry 7 }

    ssidWprSharedSecret OBJECT-TYPE
        SYNTAX          DisplayString(SIZE(0..128))
        MAX-ACCESS      read-write
        STATUS          current
        DESCRIPTION
            "Shared secret for WPR"
        ::= { ssidWprEntry 8 }

    ssidWprScreenType OBJECT-TYPE
        SYNTAX          INTEGER { splash(0), login(1), none(2) }
        MAX-ACCESS      read-write
        STATUS          current
        DESCRIPTION
            "Screen type for WPR"
        ::= { ssidWprEntry 9 }

    ssidWprScreenTimeout OBJECT-TYPE
        SYNTAX          Integer32(0..100)
        MAX-ACCESS      read-write
        STATUS          current
        DESCRIPTION
            "Splash screen timeout (0 - no timeout)"
        ::= { ssidWprEntry 10 }

    ssidWprLandingPage OBJECT-TYPE
        SYNTAX          DisplayString(SIZE(0..255))
        MAX-ACCESS      read-write
        STATUS          current
        DESCRIPTION
            "Landing page URL for WPR"
        ::= { ssidWprEntry 11 }

    ssidWprSharedSecretForm OBJECT-TYPE
        SYNTAX          INTEGER { clear(0), encrypted(1) }
        MAX-ACCESS      read-write
        STATUS          current
        DESCRIPTION
            "WPR shared secret form"
        ::= { ssidWprEntry 12 }

    ssidWprAuthType OBJECT-TYPE
        SYNTAX          INTEGER { chap(0), pap(1), ms-chap(2) }
        MAX-ACCESS      read-write
        STATUS          current
        DESCRIPTION
            "WPR authentication protocol"
        ::= { ssidWprEntry 13 }

    ssidWprHttpsEnable OBJECT-TYPE
        SYNTAX          INTEGER { disable(0), enable(1) }
        MAX-ACCESS      read-write
        STATUS          current
        DESCRIPTION
            "Enable or disable HTTPS login for WPR"
        ::= { ssidWprEntry 14 }

    ssidWprBackground OBJECT-TYPE
        SYNTAX          DisplayString(SIZE(0..50))
        MAX-ACCESS      read-write
        STATUS          current
        DESCRIPTION
            "Custom background file for WPR"
        ::= { ssidWprEntry 15 }

    ssidWprLogoImage OBJECT-TYPE
        SYNTAX          DisplayString(SIZE(0..50))
        MAX-ACCESS      read-write
        STATUS          current
        DESCRIPTION
            "Custom logo file for WPR"
        ::= { ssidWprEntry 16 }

    ssidWprHeaderText OBJECT-TYPE
        SYNTAX          DisplayString(SIZE(0..50))
        MAX-ACCESS      read-write
        STATUS          current
        DESCRIPTION
            "Custom header text file for WPR"
        ::= { ssidWprEntry 17 }

    ssidWprFooterText OBJECT-TYPE
        SYNTAX          DisplayString(SIZE(0..50))
        MAX-ACCESS      read-write
        STATUS          current
        DESCRIPTION
            "Custom footer text file for WPR"
        ::= { ssidWprEntry 18 }

    ssidWprAuthTimeout OBJECT-TYPE
        SYNTAX          Integer32(0..10080)
        MAX-ACCESS      read-write
        STATUS          current
        DESCRIPTION
            "WPR station authentication timeout in minutes (0 - no timeout)"
        ::= { ssidWprEntry 19 }

    ssidWprHttpsPassthru OBJECT-TYPE
        SYNTAX          INTEGER { disable(0), enable(1) }
        MAX-ACCESS      read-write
        STATUS          current
        DESCRIPTION
            "Enable or disable WPR HTTPS Passthru"
        ::= { ssidWprEntry 20 }

    ssidHoneypotWhitelistTable OBJECT-TYPE
        SYNTAX          SEQUENCE OF SsidHoneypotWhitelistEntry
        MAX-ACCESS      not-accessible
        STATUS          current
        DESCRIPTION
            "SSID honeypot whitelist"
        ::= { ssid 6 }

    ssidHoneypotWhitelistEntry OBJECT-TYPE
        SYNTAX          SsidHoneypotWhitelistEntry
        MAX-ACCESS      not-accessible
        STATUS          current
        DESCRIPTION
            "SSID honeypot whitelist table entry"
        INDEX       { ssidHoneypotWhitelistIndex }
        ::= { ssidHoneypotWhitelistTable 1 }

    SsidHoneypotWhitelistEntry ::= SEQUENCE {
        ssidHoneypotWhitelistIndex          Integer32,
        ssidHoneypotWhitelistSSID           DisplayString,
        ssidHoneypotWhitelistRowStatus      RowStatus
    }

    ssidHoneypotWhitelistIndex OBJECT-TYPE
        SYNTAX          Integer32
        MAX-ACCESS      not-accessible
        STATUS          current
        DESCRIPTION
            "SSID honeypot whitelist index"
        ::= { ssidHoneypotWhitelistEntry 1 }

    ssidHoneypotWhitelistSSID OBJECT-TYPE
        SYNTAX          DisplayString(SIZE(1..32))
        MAX-ACCESS      read-create
        STATUS          current
        DESCRIPTION
            "SSID name"
        ::= { ssidHoneypotWhitelistEntry 2 }

    ssidHoneypotWhitelistRowStatus OBJECT-TYPE
        SYNTAX          RowStatus
        MAX-ACCESS      read-create
        STATUS          current
        DESCRIPTION
            "Status of the SSID honeypot whitelist row entry"
        ::= { ssidHoneypotWhitelistEntry 3 }

    ssidHoneypotWhitelistTableReset OBJECT-TYPE
        SYNTAX          INTEGER { reset(1) }
        MAX-ACCESS      read-write
        STATUS          current
        DESCRIPTION
            "Reset SSID honeypot whitelist (clear all entries)"
        ::= { ssid 7 }

    ssidHoneypotBroadcastTable OBJECT-TYPE
        SYNTAX          SEQUENCE OF SsidHoneypotBroadcastEntry
        MAX-ACCESS      not-accessible
        STATUS          current
        DESCRIPTION
            "SSID honeypot broadcast"
        ::= { ssid 8 }

    ssidHoneypotBroadcastEntry OBJECT-TYPE
        SYNTAX          SsidHoneypotBroadcastEntry
        MAX-ACCESS      not-accessible
        STATUS          current
        DESCRIPTION
            "SSID honeypot broadcast table entry"
        INDEX       { ssidHoneypotBroadcastIndex }
        ::= { ssidHoneypotBroadcastTable 1 }

    SsidHoneypotBroadcastEntry ::= SEQUENCE {
        ssidHoneypotBroadcastIndex          Integer32,
        ssidHoneypotBroadcastSSID           DisplayString,
        ssidHoneypotBroadcastRowStatus      RowStatus
    }

    ssidHoneypotBroadcastIndex OBJECT-TYPE
        SYNTAX          Integer32
        MAX-ACCESS      not-accessible
        STATUS          current
        DESCRIPTION
            "SSID honeypot broadcast index"
        ::= { ssidHoneypotBroadcastEntry 1 }

    ssidHoneypotBroadcastSSID OBJECT-TYPE
        SYNTAX          DisplayString(SIZE(1..32))
        MAX-ACCESS      read-create
        STATUS          current
        DESCRIPTION
            "SSID name"
        ::= { ssidHoneypotBroadcastEntry 2 }

    ssidHoneypotBroadcastRowStatus OBJECT-TYPE
        SYNTAX          RowStatus
        MAX-ACCESS      read-create
        STATUS          current
        DESCRIPTION
            "Status of the SSID honeypot broadcast row entry"
        ::= { ssidHoneypotBroadcastEntry 3 }

    ssidHoneypotBroadcastTableReset OBJECT-TYPE
        SYNTAX          INTEGER { reset(1) }
        MAX-ACCESS      read-write
        STATUS          current
        DESCRIPTION
            "Reset SSID honeypot broadcast (clear all entries)"
        ::= { ssid 9 }

--
-- STATIONS
--

    stationAssociationTable OBJECT-TYPE
        SYNTAX          SEQUENCE OF StationAssociationEntry
        MAX-ACCESS      not-accessible
        STATUS          current
        DESCRIPTION
            "Table of stations associated with array"
        ::= { stations 1 }

    stationAssociationEntry OBJECT-TYPE
        SYNTAX          StationAssociationEntry
        MAX-ACCESS      not-accessible
        STATUS          current
        DESCRIPTION
            "Table entry for associated station"
        INDEX       { stationAssociationIndex }
        ::= { stationAssociationTable 1 }

    StationAssociationEntry ::= SEQUENCE {
        stationAssociationIndex                 Integer32,
        stationAssociationMACAddress            DisplayString,
        stationAssociationManufacturer          DisplayString,
        stationAssociationIPAddress             DisplayString,
        stationAssociationNetbiosName           DisplayString,
        stationAssociationIAP                   DisplayString,
        stationAssociationSSID                  DisplayString,
        stationAssociationVLAN                  Integer32,
        stationAssociationRSSI                  Integer32,
        stationAssociationTime                  DisplayString,
        stationAssociationTxRate                Integer32,
        stationAssociationRxRate                Integer32,
        stationAssociationRSSIa1                Integer32,
        stationAssociationRSSIa2                Integer32,
        stationAssociationRSSIa3                Integer32,
        stationAssociationRSSIa4                Integer32,
        stationAssociationRSSIa5                Integer32,
        stationAssociationRSSIa6                Integer32,
        stationAssociationRSSIa7                Integer32,
        stationAssociationRSSIa8                Integer32,
        stationAssociationRSSIa9                Integer32,
        stationAssociationRSSIa10               Integer32,
        stationAssociationRSSIa11               Integer32,
        stationAssociationRSSIa12               Integer32,
        stationAssociationRSSIabg1              Integer32,
        stationAssociationRSSIabg2              Integer32,
        stationAssociationRSSIabg3              Integer32,
        stationAssociationRSSIabg4              Integer32,
        stationAssociationEncType               INTEGER,
        stationAssociationCipher                INTEGER,
        stationAssociationKeyMgmt               INTEGER,
        stationAssociationBand                  INTEGER,
        stationAssociationChannel               Integer32,
        stationAssociationMediaType             INTEGER,
        stationAssociationUserName              DisplayString,
        stationAssociationTimeRSSIa1            Counter32,
        stationAssociationTimeRSSIa2            Counter32,
        stationAssociationTimeRSSIa3            Counter32,
        stationAssociationTimeRSSIa4            Counter32,
        stationAssociationTimeRSSIa5            Counter32,
        stationAssociationTimeRSSIa6            Counter32,
        stationAssociationTimeRSSIa7            Counter32,
        stationAssociationTimeRSSIa8            Counter32,
        stationAssociationTimeRSSIa9            Counter32,
        stationAssociationTimeRSSIa10           Counter32,
        stationAssociationTimeRSSIa11           Counter32,
        stationAssociationTimeRSSIa12           Counter32,
        stationAssociationTimeRSSIabg1          Counter32,
        stationAssociationTimeRSSIabg2          Counter32,
        stationAssociationTimeRSSIabg3          Counter32,
        stationAssociationTimeRSSIabg4          Counter32,
        stationAssociationHostname              DisplayString,
        stationAssociationDeviceType            DisplayString,
        stationAssociationDeviceClass           DisplayString,
        stationAssociationUserAgent             DisplayString,
        stationAssociationDeviceSource          INTEGER,
        stationAssociationDeviceSourceIndex     Integer32,
        stationAssociationOperatingMode         INTEGER
    }

    stationAssociationIndex OBJECT-TYPE
        SYNTAX          Integer32
        MAX-ACCESS      not-accessible
        STATUS          current
        DESCRIPTION
            "Station association index"
        ::= { stationAssociationEntry 1 }

    stationAssociationMACAddress OBJECT-TYPE
        SYNTAX          DisplayString
        MAX-ACCESS      read-only
        STATUS          current
        DESCRIPTION
            "MAC address of the station"
        ::= { stationAssociationEntry 2 }

    stationAssociationManufacturer OBJECT-TYPE
        SYNTAX          DisplayString
        MAX-ACCESS      read-only
        STATUS          current
        DESCRIPTION
            "Manufacturer of the station's network card"
        ::= { stationAssociationEntry 3 }

    stationAssociationIPAddress OBJECT-TYPE
        SYNTAX          DisplayString
        MAX-ACCESS      read-only
        STATUS          current
        DESCRIPTION
            "IP Address of the station"
        ::= { stationAssociationEntry 4 }

    stationAssociationNetbiosName OBJECT-TYPE
        SYNTAX          DisplayString
        MAX-ACCESS      read-only
        STATUS          current
        DESCRIPTION
            "Netbios name of the station"
        ::= { stationAssociationEntry 5 }

    stationAssociationIAP OBJECT-TYPE
        SYNTAX          DisplayString
        MAX-ACCESS      read-only
        STATUS          current
        DESCRIPTION
            "IAP station associated with"
        ::= { stationAssociationEntry 6 }

    stationAssociationSSID OBJECT-TYPE
        SYNTAX          DisplayString
        MAX-ACCESS      read-only
        STATUS          current
        DESCRIPTION
            "SSID station associated with"
        ::= { stationAssociationEntry 7 }

    stationAssociationVLAN OBJECT-TYPE
        SYNTAX          Integer32
        MAX-ACCESS      read-only
        STATUS          current
        DESCRIPTION
            "VLAN of the station"
        ::= { stationAssociationEntry 8 }

    stationAssociationRSSI OBJECT-TYPE
        SYNTAX          Integer32
        MAX-ACCESS      read-only
        STATUS          current
        DESCRIPTION
            "Station's RSSI (last packet received)"
        ::= { stationAssociationEntry 9 }

    stationAssociationTime OBJECT-TYPE
        SYNTAX          DisplayString
        MAX-ACCESS      read-only
        STATUS          current
        DESCRIPTION
            "Time (in D:H:M) station is associated"
        ::= { stationAssociationEntry 10 }

    stationAssociationTxRate OBJECT-TYPE
        SYNTAX          Integer32
        MAX-ACCESS      read-only
        STATUS          current
        DESCRIPTION
            "Tx rate of the station"
        ::= { stationAssociationEntry 11 }

    stationAssociationRxRate OBJECT-TYPE
        SYNTAX          Integer32
        MAX-ACCESS      read-only
        STATUS          current
        DESCRIPTION
            "Rx rate of the station"
        ::= { stationAssociationEntry 12 }

    stationAssociationRSSIa1 OBJECT-TYPE
        SYNTAX          Integer32
        MAX-ACCESS      read-only
        STATUS          current
        DESCRIPTION
            "Station's RSSI for last Probe Request on IAP a1"
        ::= { stationAssociationEntry 13 }

    stationAssociationRSSIa2 OBJECT-TYPE
        SYNTAX          Integer32
        MAX-ACCESS      read-only
        STATUS          current
        DESCRIPTION
            "Station's RSSI for last Probe Request on IAP a2"
        ::= { stationAssociationEntry 14 }

    stationAssociationRSSIa3 OBJECT-TYPE
        SYNTAX          Integer32
        MAX-ACCESS      read-only
        STATUS          current
        DESCRIPTION
            "Station's RSSI for last Probe Request on IAP a3"
        ::= { stationAssociationEntry 15 }

    stationAssociationRSSIa4 OBJECT-TYPE
        SYNTAX          Integer32
        MAX-ACCESS      read-only
        STATUS          current
        DESCRIPTION
            "Station's RSSI for last Probe Request on IAP a4"
        ::= { stationAssociationEntry 16 }

    stationAssociationRSSIa5 OBJECT-TYPE
        SYNTAX          Integer32
        MAX-ACCESS      read-only
        STATUS          current
        DESCRIPTION
            "Station's RSSI for last Probe Request on IAP a5"
        ::= { stationAssociationEntry 17 }

    stationAssociationRSSIa6 OBJECT-TYPE
        SYNTAX          Integer32
        MAX-ACCESS      read-only
        STATUS          current
        DESCRIPTION
            "Station's RSSI for last Probe Request on IAP a6"
        ::= { stationAssociationEntry 18 }

    stationAssociationRSSIa7 OBJECT-TYPE
        SYNTAX          Integer32
        MAX-ACCESS      read-only
        STATUS          current
        DESCRIPTION
            "Station's RSSI for last Probe Request on IAP a7"
        ::= { stationAssociationEntry 19 }

    stationAssociationRSSIa8 OBJECT-TYPE
        SYNTAX          Integer32
        MAX-ACCESS      read-only
        STATUS          current
        DESCRIPTION
            "Station's RSSI for last Probe Request on IAP a8"
        ::= { stationAssociationEntry 20 }

    stationAssociationRSSIa9 OBJECT-TYPE
        SYNTAX          Integer32
        MAX-ACCESS      read-only
        STATUS          current
        DESCRIPTION
            "Station's RSSI for last Probe Request on IAP a9"
        ::= { stationAssociationEntry 21 }

    stationAssociationRSSIa10 OBJECT-TYPE
        SYNTAX          Integer32
        MAX-ACCESS      read-only
        STATUS          current
        DESCRIPTION
            "Station's RSSI for last Probe Request on IAP a10"
        ::= { stationAssociationEntry 22 }

    stationAssociationRSSIa11 OBJECT-TYPE
        SYNTAX          Integer32
        MAX-ACCESS      read-only
        STATUS          current
        DESCRIPTION
            "Station's RSSI for last Probe Request on IAP a11"
        ::= { stationAssociationEntry 23 }

    stationAssociationRSSIa12 OBJECT-TYPE
        SYNTAX          Integer32
        MAX-ACCESS      read-only
        STATUS          current
        DESCRIPTION
            "Station's RSSI for last Probe Request on IAP a12"
        ::= { stationAssociationEntry 24 }

    stationAssociationRSSIabg1 OBJECT-TYPE
        SYNTAX          Integer32
        MAX-ACCESS      read-only
        STATUS          current
        DESCRIPTION
            "Station's RSSI for last Probe Request on IAP abg1"
        ::= { stationAssociationEntry 25 }

    stationAssociationRSSIabg2 OBJECT-TYPE
        SYNTAX          Integer32
        MAX-ACCESS      read-only
        STATUS          current
        DESCRIPTION
            "Station's RSSI for last Probe Request on IAP abg2"
        ::= { stationAssociationEntry 26 }

    stationAssociationRSSIabg3 OBJECT-TYPE
        SYNTAX          Integer32
        MAX-ACCESS      read-only
        STATUS          current
        DESCRIPTION
            "Station's RSSI for last Probe Request on IAP abg3"
        ::= { stationAssociationEntry 27 }

    stationAssociationRSSIabg4 OBJECT-TYPE
        SYNTAX          Integer32
        MAX-ACCESS      read-only
        STATUS          current
        DESCRIPTION
            "Station's RSSI for last Probe Request on IAP abg4"
        ::= { stationAssociationEntry 28 }

    stationAssociationEncType OBJECT-TYPE
        SYNTAX          INTEGER { none(0), wep(1), wpa(2), wpa2(3) }
        MAX-ACCESS      read-only
        STATUS          current
        DESCRIPTION
            "Station encryption type"
        ::= { stationAssociationEntry 29 }

    stationAssociationCipher OBJECT-TYPE
        SYNTAX          INTEGER { none(0), rc4(1), tkip(2), aes(3) }
        MAX-ACCESS      read-only
        STATUS          current
        DESCRIPTION
            "Cipher suite used by station"
        ::= { stationAssociationEntry 30 }

    stationAssociationKeyMgmt OBJECT-TYPE
        SYNTAX          INTEGER { none(0), eap(1), psk(2) }
        MAX-ACCESS      read-only
        STATUS          current
        DESCRIPTION
            "Key management algorithm used by station"
        ::= { stationAssociationEntry 31 }

    stationAssociationBand OBJECT-TYPE
        SYNTAX          INTEGER { dot11a(0),  dot11bg(1) }
        MAX-ACCESS      read-only
        STATUS          current
        DESCRIPTION
            "802.11 band station is on"
        ::= { stationAssociationEntry 32 }

    stationAssociationChannel OBJECT-TYPE
        SYNTAX          Integer32
        MAX-ACCESS      read-only
        STATUS          current
        DESCRIPTION
            "Channel station is on"
        ::= { stationAssociationEntry 33 }

    stationAssociationMediaType OBJECT-TYPE
        SYNTAX          INTEGER { dot11b(1), dot11bg(2), dot11abg(3), dot11a(4),
                                  dot11ab(5), dot11ag(6), dot11g(7), dot11n(8),
                                  dot11bn(9), dot11gn(10), dot11bgn(11), dot11an(12),
                                  dot11abn(13), dot11agn(14), dot11abgn(15),
                                  dot11anac(16), dot11abgnac(17)  }
        MAX-ACCESS      read-only
        STATUS          current
        DESCRIPTION
            "Station media type"
        ::= { stationAssociationEntry 34 }

    stationAssociationUserName OBJECT-TYPE
        SYNTAX          DisplayString
        MAX-ACCESS      read-only
        STATUS          current
        DESCRIPTION
            "Station user name"
        ::= { stationAssociationEntry 35 }

    stationAssociationTimeRSSIa1 OBJECT-TYPE
        SYNTAX          Counter32
        MAX-ACCESS      read-only
        STATUS          current
        DESCRIPTION
            "Station's elapsed time since last Probe Request on IAP a1 (milliseconds)"
        ::= { stationAssociationEntry 36 }

    stationAssociationTimeRSSIa2 OBJECT-TYPE
        SYNTAX          Counter32
        MAX-ACCESS      read-only
        STATUS          current
        DESCRIPTION
            "Station's elapsed time since last Probe Request on IAP a2 (milliseconds)"
        ::= { stationAssociationEntry 37 }

    stationAssociationTimeRSSIa3 OBJECT-TYPE
        SYNTAX          Counter32
        MAX-ACCESS      read-only
        STATUS          current
        DESCRIPTION
            "Station's elapsed time since last Probe Request on IAP a3 (milliseconds)"
        ::= { stationAssociationEntry 38 }

    stationAssociationTimeRSSIa4 OBJECT-TYPE
        SYNTAX          Counter32
        MAX-ACCESS      read-only
        STATUS          current
        DESCRIPTION
            "Station's elapsed time since last Probe Request on IAP a4 (milliseconds)"
        ::= { stationAssociationEntry 39 }

    stationAssociationTimeRSSIa5 OBJECT-TYPE
        SYNTAX          Counter32
        MAX-ACCESS      read-only
        STATUS          current
        DESCRIPTION
            "Station's elapsed time since last Probe Request on IAP a5 (milliseconds)"
        ::= { stationAssociationEntry 40 }

    stationAssociationTimeRSSIa6 OBJECT-TYPE
        SYNTAX          Counter32
        MAX-ACCESS      read-only
        STATUS          current
        DESCRIPTION
            "Station's elapsed time since last Probe Request on IAP a6 (milliseconds)"
        ::= { stationAssociationEntry 41 }

    stationAssociationTimeRSSIa7 OBJECT-TYPE
        SYNTAX          Counter32
        MAX-ACCESS      read-only
        STATUS          current
        DESCRIPTION
            "Station's elapsed time since last Probe Request on IAP a7 (milliseconds)"
        ::= { stationAssociationEntry 42 }

    stationAssociationTimeRSSIa8 OBJECT-TYPE
        SYNTAX          Counter32
        MAX-ACCESS      read-only
        STATUS          current
        DESCRIPTION
            "Station's elapsed time since last Probe Request on IAP a8 (milliseconds)"
        ::= { stationAssociationEntry 43 }

    stationAssociationTimeRSSIa9 OBJECT-TYPE
        SYNTAX          Counter32
        MAX-ACCESS      read-only
        STATUS          current
        DESCRIPTION
            "Station's elapsed time since last Probe Request on IAP a9 (milliseconds)"
        ::= { stationAssociationEntry 44 }

    stationAssociationTimeRSSIa10 OBJECT-TYPE
        SYNTAX          Counter32
        MAX-ACCESS      read-only
        STATUS          current
        DESCRIPTION
            "Station's elapsed time since last Probe Request on IAP a10 (milliseconds)"
        ::= { stationAssociationEntry 45 }

    stationAssociationTimeRSSIa11 OBJECT-TYPE
        SYNTAX          Counter32
        MAX-ACCESS      read-only
        STATUS          current
        DESCRIPTION
            "Station's elapsed time since last Probe Request on IAP a11 (milliseconds)"
        ::= { stationAssociationEntry 46 }

    stationAssociationTimeRSSIa12 OBJECT-TYPE
        SYNTAX          Counter32
        MAX-ACCESS      read-only
        STATUS          current
        DESCRIPTION
            "Station's elapsed time since last Probe Request on IAP a12 (milliseconds)"
        ::= { stationAssociationEntry 47 }

    stationAssociationTimeRSSIabg1 OBJECT-TYPE
        SYNTAX          Counter32
        MAX-ACCESS      read-only
        STATUS          current
        DESCRIPTION
            "Station's elapsed time since last Probe Request on IAP abg1 (milliseconds)"
        ::= { stationAssociationEntry 48 }

    stationAssociationTimeRSSIabg2 OBJECT-TYPE
        SYNTAX          Counter32
        MAX-ACCESS      read-only
        STATUS          current
        DESCRIPTION
            "Station's elapsed time since last Probe Request on IAP abg2 (milliseconds)"
        ::= { stationAssociationEntry 49 }

    stationAssociationTimeRSSIabg3 OBJECT-TYPE
        SYNTAX          Counter32
        MAX-ACCESS      read-only
        STATUS          current
        DESCRIPTION
            "Station's elapsed time since last Probe Request on IAP abg3 (milliseconds)"
        ::= { stationAssociationEntry 50 }

    stationAssociationTimeRSSIabg4 OBJECT-TYPE
        SYNTAX          Counter32
        MAX-ACCESS      read-only
        STATUS          current
        DESCRIPTION
            "Station's elapsed time since last Probe Request on IAP abg4 (milliseconds)"
        ::= { stationAssociationEntry 51 }

    stationAssociationHostname OBJECT-TYPE
        SYNTAX          DisplayString
        MAX-ACCESS      read-only
        STATUS          current
        DESCRIPTION
            "Station hostname"
        ::= { stationAssociationEntry 52 }

    stationAssociationDeviceType OBJECT-TYPE
        SYNTAX          DisplayString
        MAX-ACCESS      read-only
        STATUS          current
        DESCRIPTION
            "Station device type"
        ::= { stationAssociationEntry 53 }

    stationAssociationDeviceClass OBJECT-TYPE
        SYNTAX          DisplayString
        MAX-ACCESS      read-only
        STATUS          current
        DESCRIPTION
            "Station device class"
        ::= { stationAssociationEntry 54 }

    stationAssociationUserAgent OBJECT-TYPE
        SYNTAX          DisplayString
        MAX-ACCESS      read-only
        STATUS          current
        DESCRIPTION
            "User-agent string"
        ::= { stationAssociationEntry 55 }

    stationAssociationDeviceSource OBJECT-TYPE
        SYNTAX          INTEGER { none(0), manufacturer(1), netbios-name(2),
                                  dhcp-hostname(3), user-agent-string(4),
                                  internal-rules(5), external-rules(6), cache(7) }
        MAX-ACCESS      read-only
        STATUS          current
        DESCRIPTION
            "Station device source"
        ::= { stationAssociationEntry 56 }

    stationAssociationDeviceSourceIndex OBJECT-TYPE
        SYNTAX          Integer32
        MAX-ACCESS      read-only
        STATUS          current
        DESCRIPTION
            "Station device source index"
        ::= { stationAssociationEntry 57 }

    stationAssociationOperatingMode OBJECT-TYPE
        SYNTAX          INTEGER { none(0),b(1),g(2),bg(3),a(4),
                                  ab(5),ag(6),abg(7),n(8),bn(9),
                                  gn(10),bgn(11),an(12),abn(13),
                                  agn(14),abgn(15),ac(16),bac(17),
                                  gac(18),bgac(19),aac(20),abac(21),
                                  agac(22),abgac(23),nac(24),bnac(25),
                                  gnac(26),bgnac(27),anac(28),abnac(29),
                                  agnac(30),abgnac(31) }
        MAX-ACCESS      read-only
        STATUS          current
        DESCRIPTION
            "Station Operating Mode"
        ::= { stationAssociationEntry 58 }


    stationUnassociatedTable OBJECT-TYPE
        SYNTAX          SEQUENCE OF StationUnassociatedEntry
        MAX-ACCESS      not-accessible
        STATUS          current
        DESCRIPTION
            "Table of unassociated stations"
        ::= { stations 2 }

    stationUnassociatedEntry OBJECT-TYPE
        SYNTAX          StationUnassociatedEntry
        MAX-ACCESS      not-accessible
        STATUS          current
        DESCRIPTION
            "Table entry for unassociated station"
        INDEX       { stationUnassociatedIndex }
        ::= { stationUnassociatedTable 1 }

    StationUnassociatedEntry ::= SEQUENCE {
        stationUnassociatedIndex            Integer32,
        stationUnassociatedMACAddress       DisplayString,
        stationUnassociatedManufacturer     DisplayString,
        stationUnassociatedNetbiosName      DisplayString,
        stationUnassociatedMediaType        INTEGER,
        stationUnassociatedTxRate           Integer32,
        stationUnassociatedRxRate           Integer32,
        stationUnassociatedRSSI             Integer32,
        stationUnassociatedTime             Counter32,
        stationUnassociatedRSSIa1           Integer32,
        stationUnassociatedRSSIa2           Integer32,
        stationUnassociatedRSSIa3           Integer32,
        stationUnassociatedRSSIa4           Integer32,
        stationUnassociatedRSSIa5           Integer32,
        stationUnassociatedRSSIa6           Integer32,
        stationUnassociatedRSSIa7           Integer32,
        stationUnassociatedRSSIa8           Integer32,
        stationUnassociatedRSSIa9           Integer32,
        stationUnassociatedRSSIa10          Integer32,
        stationUnassociatedRSSIa11          Integer32,
        stationUnassociatedRSSIa12          Integer32,
        stationUnassociatedRSSIabg1         Integer32,
        stationUnassociatedRSSIabg2         Integer32,
        stationUnassociatedRSSIabg3         Integer32,
        stationUnassociatedRSSIabg4         Integer32,
        stationUnassociatedTimeRSSIa1       Counter32,
        stationUnassociatedTimeRSSIa2       Counter32,
        stationUnassociatedTimeRSSIa3       Counter32,
        stationUnassociatedTimeRSSIa4       Counter32,
        stationUnassociatedTimeRSSIa5       Counter32,
        stationUnassociatedTimeRSSIa6       Counter32,
        stationUnassociatedTimeRSSIa7       Counter32,
        stationUnassociatedTimeRSSIa8       Counter32,
        stationUnassociatedTimeRSSIa9       Counter32,
        stationUnassociatedTimeRSSIa10      Counter32,
        stationUnassociatedTimeRSSIa11      Counter32,
        stationUnassociatedTimeRSSIa12      Counter32,
        stationUnassociatedTimeRSSIabg1     Counter32,
        stationUnassociatedTimeRSSIabg2     Counter32,
        stationUnassociatedTimeRSSIabg3     Counter32,
        stationUnassociatedTimeRSSIabg4     Counter32
    }

    stationUnassociatedIndex OBJECT-TYPE
        SYNTAX          Integer32
        MAX-ACCESS      not-accessible
        STATUS          current
        DESCRIPTION
            "Station index"
        ::= { stationUnassociatedEntry 1 }

    stationUnassociatedMACAddress OBJECT-TYPE
        SYNTAX          DisplayString
        MAX-ACCESS      read-only
        STATUS          current
        DESCRIPTION
            "MAC address of the station"
        ::= { stationUnassociatedEntry 2 }

    stationUnassociatedManufacturer OBJECT-TYPE
        SYNTAX          DisplayString
        MAX-ACCESS      read-only
        STATUS          current
        DESCRIPTION
            "Manufacturer of the station's network card"
        ::= { stationUnassociatedEntry 3 }

    stationUnassociatedNetbiosName OBJECT-TYPE
        SYNTAX          DisplayString
        MAX-ACCESS      read-only
        STATUS          current
        DESCRIPTION
            "Netbios name of the station"
        ::= { stationUnassociatedEntry 4 }

    stationUnassociatedMediaType OBJECT-TYPE
        SYNTAX          INTEGER { dot11b(1), dot11bg(2), dot11abg(3), dot11a(4),
                                  dot11ab(5), dot11ag(6), dot11g(7), dot11n(8),
                                  dot11bn(9), dot11gn(10), dot11bgn(11), dot11an(12),
                                  dot11abn(13), dot11agn(14), dot11abgn(15),
                                  dot11anac(16), dot11abgnac(17)  }
        MAX-ACCESS      read-only
        STATUS          current
        DESCRIPTION
            "Station media type"
        ::= { stationUnassociatedEntry 5 }

    stationUnassociatedTxRate OBJECT-TYPE
        SYNTAX          Integer32
        MAX-ACCESS      read-only
        STATUS          current
        DESCRIPTION
            "Tx rate of the station"
        ::= { stationUnassociatedEntry 6 }

    stationUnassociatedRxRate OBJECT-TYPE
        SYNTAX          Integer32
        MAX-ACCESS      read-only
        STATUS          current
        DESCRIPTION
            "Rx rate of the station"
        ::= { stationUnassociatedEntry 7 }

    stationUnassociatedRSSI OBJECT-TYPE
        SYNTAX          Integer32
        MAX-ACCESS      read-only
        STATUS          current
        DESCRIPTION
            "Station's RSSI (last packet received)"
        ::= { stationUnassociatedEntry 8 }

    stationUnassociatedTime OBJECT-TYPE
        SYNTAX          Counter32
        MAX-ACCESS      read-only
        STATUS          current
        DESCRIPTION
            "Time (in seconds) since Rx"
        ::= { stationUnassociatedEntry 9 }

    stationUnassociatedRSSIa1 OBJECT-TYPE
        SYNTAX          Integer32
        MAX-ACCESS      read-only
        STATUS          current
        DESCRIPTION
            "Station's RSSI for last Probe Request on IAP a1"
        ::= { stationUnassociatedEntry 10 }

    stationUnassociatedRSSIa2 OBJECT-TYPE
        SYNTAX          Integer32
        MAX-ACCESS      read-only
        STATUS          current
        DESCRIPTION
            "Station's RSSI for last Probe Request on IAP a2"
        ::= { stationUnassociatedEntry 11 }

    stationUnassociatedRSSIa3 OBJECT-TYPE
        SYNTAX          Integer32
        MAX-ACCESS      read-only
        STATUS          current
        DESCRIPTION
            "Station's RSSI for last Probe Request on IAP a3"
        ::= { stationUnassociatedEntry 12 }

    stationUnassociatedRSSIa4 OBJECT-TYPE
        SYNTAX          Integer32
        MAX-ACCESS      read-only
        STATUS          current
        DESCRIPTION
            "Station's RSSI for last Probe Request on IAP a4"
        ::= { stationUnassociatedEntry 13 }

    stationUnassociatedRSSIa5 OBJECT-TYPE
        SYNTAX          Integer32
        MAX-ACCESS      read-only
        STATUS          current
        DESCRIPTION
            "Station's RSSI for last Probe Request on IAP a5"
        ::= { stationUnassociatedEntry 14 }

    stationUnassociatedRSSIa6 OBJECT-TYPE
        SYNTAX          Integer32
        MAX-ACCESS      read-only
        STATUS          current
        DESCRIPTION
            "Station's RSSI for last Probe Request on IAP a6"
        ::= { stationUnassociatedEntry 15 }

    stationUnassociatedRSSIa7 OBJECT-TYPE
        SYNTAX          Integer32
        MAX-ACCESS      read-only
        STATUS          current
        DESCRIPTION
            "Station's RSSI for last Probe Request on IAP a7"
        ::= { stationUnassociatedEntry 16 }

    stationUnassociatedRSSIa8 OBJECT-TYPE
        SYNTAX          Integer32
        MAX-ACCESS      read-only
        STATUS          current
        DESCRIPTION
            "Station's RSSI for last Probe Request on IAP a8"
        ::= { stationUnassociatedEntry 17 }

    stationUnassociatedRSSIa9 OBJECT-TYPE
        SYNTAX          Integer32
        MAX-ACCESS      read-only
        STATUS          current
        DESCRIPTION
            "Station's RSSI for last Probe Request on IAP a9"
        ::= { stationUnassociatedEntry 18 }

    stationUnassociatedRSSIa10 OBJECT-TYPE
        SYNTAX          Integer32
        MAX-ACCESS      read-only
        STATUS          current
        DESCRIPTION
            "Station's RSSI for last Probe Request on IAP a10"
        ::= { stationUnassociatedEntry 19 }

    stationUnassociatedRSSIa11 OBJECT-TYPE
        SYNTAX          Integer32
        MAX-ACCESS      read-only
        STATUS          current
        DESCRIPTION
            "Station's RSSI for last Probe Request on IAP a11"
        ::= { stationUnassociatedEntry 20 }

    stationUnassociatedRSSIa12 OBJECT-TYPE
        SYNTAX          Integer32
        MAX-ACCESS      read-only
        STATUS          current
        DESCRIPTION
            "Station's RSSI for last Probe Request on IAP a12"
        ::= { stationUnassociatedEntry 21 }

    stationUnassociatedRSSIabg1 OBJECT-TYPE
        SYNTAX          Integer32
        MAX-ACCESS      read-only
        STATUS          current
        DESCRIPTION
            "Station's RSSI for last Probe Request on IAP abg1"
        ::= { stationUnassociatedEntry 22 }

    stationUnassociatedRSSIabg2 OBJECT-TYPE
        SYNTAX          Integer32
        MAX-ACCESS      read-only
        STATUS          current
        DESCRIPTION
            "Station's RSSI for last Probe Request on IAP abg2"
        ::= { stationUnassociatedEntry 23 }

    stationUnassociatedRSSIabg3 OBJECT-TYPE
        SYNTAX          Integer32
        MAX-ACCESS      read-only
        STATUS          current
        DESCRIPTION
            "Station's RSSI for last Probe Request on IAP abg3"
        ::= { stationUnassociatedEntry 24 }

    stationUnassociatedRSSIabg4 OBJECT-TYPE
        SYNTAX          Integer32
        MAX-ACCESS      read-only
        STATUS          current
        DESCRIPTION
            "Station's RSSI for last Probe Request on IAP abg4"
        ::= { stationUnassociatedEntry 25 }

    stationUnassociatedTimeRSSIa1 OBJECT-TYPE
        SYNTAX          Counter32
        MAX-ACCESS      read-only
        STATUS          current
        DESCRIPTION
            "Station's elapsed time since last Probe Request on last Probe Request on IAP a1 (milliseconds)"
        ::= { stationUnassociatedEntry 26 }

    stationUnassociatedTimeRSSIa2 OBJECT-TYPE
        SYNTAX          Counter32
        MAX-ACCESS      read-only
        STATUS          current
        DESCRIPTION
            "Station's elapsed time since last Probe Request on last Probe Request on IAP a2 (milliseconds)"
        ::= { stationUnassociatedEntry 27 }

    stationUnassociatedTimeRSSIa3 OBJECT-TYPE
        SYNTAX          Counter32
        MAX-ACCESS      read-only
        STATUS          current
        DESCRIPTION
            "Station's elapsed time since last Probe Request on last Probe Request on IAP a3 (milliseconds)"
        ::= { stationUnassociatedEntry 28 }

    stationUnassociatedTimeRSSIa4 OBJECT-TYPE
        SYNTAX          Counter32
        MAX-ACCESS      read-only
        STATUS          current
        DESCRIPTION
            "Station's elapsed time since last Probe Request on last Probe Request on IAP a4 (milliseconds)"
        ::= { stationUnassociatedEntry 29 }

    stationUnassociatedTimeRSSIa5 OBJECT-TYPE
        SYNTAX          Counter32
        MAX-ACCESS      read-only
        STATUS          current
        DESCRIPTION
            "Station's elapsed time since last Probe Request on last Probe Request on IAP a5 (milliseconds)"
        ::= { stationUnassociatedEntry 30 }

    stationUnassociatedTimeRSSIa6 OBJECT-TYPE
        SYNTAX          Counter32
        MAX-ACCESS      read-only
        STATUS          current
        DESCRIPTION
            "Station's elapsed time since last Probe Request on last Probe Request on IAP a6 (milliseconds)"
        ::= { stationUnassociatedEntry 31 }

    stationUnassociatedTimeRSSIa7 OBJECT-TYPE
        SYNTAX          Counter32
        MAX-ACCESS      read-only
        STATUS          current
        DESCRIPTION
            "Station's elapsed time since last Probe Request on last Probe Request on IAP a7 (milliseconds)"
        ::= { stationUnassociatedEntry 32 }

    stationUnassociatedTimeRSSIa8 OBJECT-TYPE
        SYNTAX          Counter32
        MAX-ACCESS      read-only
        STATUS          current
        DESCRIPTION
            "Station's elapsed time since last Probe Request on last Probe Request on IAP a8 (milliseconds)"
        ::= { stationUnassociatedEntry 33 }

    stationUnassociatedTimeRSSIa9 OBJECT-TYPE
        SYNTAX          Counter32
        MAX-ACCESS      read-only
        STATUS          current
        DESCRIPTION
            "Station's elapsed time since last Probe Request on last Probe Request on IAP a9 (milliseconds)"
        ::= { stationUnassociatedEntry 34 }

    stationUnassociatedTimeRSSIa10 OBJECT-TYPE
        SYNTAX          Counter32
        MAX-ACCESS      read-only
        STATUS          current
        DESCRIPTION
            "Station's elapsed time since last Probe Request on last Probe Request on IAP a10 (milliseconds)"
        ::= { stationUnassociatedEntry 35 }

    stationUnassociatedTimeRSSIa11 OBJECT-TYPE
        SYNTAX          Counter32
        MAX-ACCESS      read-only
        STATUS          current
        DESCRIPTION
            "Station's elapsed time since last Probe Request on last Probe Request on IAP a11 (milliseconds)"
        ::= { stationUnassociatedEntry 36 }

    stationUnassociatedTimeRSSIa12 OBJECT-TYPE
        SYNTAX          Counter32
        MAX-ACCESS      read-only
        STATUS          current
        DESCRIPTION
            "Station's elapsed time since last Probe Request on last Probe Request on IAP a12 (milliseconds)"
        ::= { stationUnassociatedEntry 37 }

    stationUnassociatedTimeRSSIabg1 OBJECT-TYPE
        SYNTAX          Counter32
        MAX-ACCESS      read-only
        STATUS          current
        DESCRIPTION
            "Station's elapsed time since last Probe Request on last Probe Request on IAP abg1 (milliseconds)"
        ::= { stationUnassociatedEntry 38 }

    stationUnassociatedTimeRSSIabg2 OBJECT-TYPE
        SYNTAX          Counter32
        MAX-ACCESS      read-only
        STATUS          current
        DESCRIPTION
            "Station's elapsed time since last Probe Request on last Probe Request on IAP abg2 (milliseconds)"
        ::= { stationUnassociatedEntry 39 }

    stationUnassociatedTimeRSSIabg3 OBJECT-TYPE
        SYNTAX          Counter32
        MAX-ACCESS      read-only
        STATUS          current
        DESCRIPTION
            "Station's elapsed time since last Probe Request on last Probe Request on IAP abg3 (milliseconds)"
        ::= { stationUnassociatedEntry 40 }

    stationUnassociatedTimeRSSIabg4 OBJECT-TYPE
        SYNTAX          Counter32
        MAX-ACCESS      read-only
        STATUS          current
        DESCRIPTION
            "Station's elapsed time since last Probe Request on last Probe Request on IAP abg4 (milliseconds)"
        ::= { stationUnassociatedEntry 41 }

    stationDeauthMacAddress OBJECT-TYPE
        SYNTAX          DisplayString(SIZE(12..17))
        MAX-ACCESS      read-write
        STATUS          current
        DESCRIPTION
            "Mac address of the station to deauthenticate"
        ::= { stations 3 }

    stationAssocTable OBJECT-TYPE
        SYNTAX          SEQUENCE OF StationAssocEntry
        MAX-ACCESS      not-accessible
        STATUS          current
        DESCRIPTION
            "Table of stations (indexed by station MAC address) associated with array"
        ::= { stations 4 }

    stationAssocEntry OBJECT-TYPE
        SYNTAX          StationAssocEntry
        MAX-ACCESS      not-accessible
        STATUS          current
        DESCRIPTION
            "Table entry for associated station"
        INDEX       { stationAssocMACAddress }
        ::= { stationAssocTable 1 }

    StationAssocEntry ::= SEQUENCE {
        stationAssocMACAddress          DisplayString,
        stationAssocManufacturer        DisplayString,
        stationAssocIPAddress           DisplayString,
        stationAssocNetbiosName         DisplayString,
        stationAssocIAP                 DisplayString,
        stationAssocSSID                DisplayString,
        stationAssocVLAN                Integer32,
        stationAssocRSSI                Integer32,
        stationAssocTime                DisplayString,
        stationAssocTxRate              Integer32,
        stationAssocRxRate              Integer32,
        stationAssocRSSIa1              Integer32,
        stationAssocRSSIa2              Integer32,
        stationAssocRSSIa3              Integer32,
        stationAssocRSSIa4              Integer32,
        stationAssocRSSIa5              Integer32,
        stationAssocRSSIa6              Integer32,
        stationAssocRSSIa7              Integer32,
        stationAssocRSSIa8              Integer32,
        stationAssocRSSIa9              Integer32,
        stationAssocRSSIa10             Integer32,
        stationAssocRSSIa11             Integer32,
        stationAssocRSSIa12             Integer32,
        stationAssocRSSIabg1            Integer32,
        stationAssocRSSIabg2            Integer32,
        stationAssocRSSIabg3            Integer32,
        stationAssocRSSIabg4            Integer32,
        stationAssocEncType             INTEGER,
        stationAssocCipher              INTEGER,
        stationAssocKeyMgmt             INTEGER,
        stationAssocBand                INTEGER,
        stationAssocChannel             Integer32,
        stationAssocMediaType           INTEGER,
        stationAssocUserName            DisplayString,
        stationAssocTimeRSSIa1          Counter32,
        stationAssocTimeRSSIa2          Counter32,
        stationAssocTimeRSSIa3          Counter32,
        stationAssocTimeRSSIa4          Counter32,
        stationAssocTimeRSSIa5          Counter32,
        stationAssocTimeRSSIa6          Counter32,
        stationAssocTimeRSSIa7          Counter32,
        stationAssocTimeRSSIa8          Counter32,
        stationAssocTimeRSSIa9          Counter32,
        stationAssocTimeRSSIa10         Counter32,
        stationAssocTimeRSSIa11         Counter32,
        stationAssocTimeRSSIa12         Counter32,
        stationAssocTimeRSSIabg1        Counter32,
        stationAssocTimeRSSIabg2        Counter32,
        stationAssocTimeRSSIabg3        Counter32,
        stationAssocTimeRSSIabg4        Counter32,
        stationAssocHostname            DisplayString,
        stationAssocDeviceType          DisplayString,
        stationAssocDeviceClass         DisplayString,
        stationAssocUserAgent           DisplayString,
        stationAssocDeviceSource        INTEGER,
        stationAssocDeviceSourceIndex   Integer32
    }

    stationAssocMACAddress OBJECT-TYPE
        SYNTAX          DisplayString
        MAX-ACCESS      read-only
        STATUS          current
        DESCRIPTION
            "MAC address of the station"
        ::= { stationAssocEntry 1 }

    stationAssocManufacturer OBJECT-TYPE
        SYNTAX          DisplayString
        MAX-ACCESS      read-only
        STATUS          current
        DESCRIPTION
            "Manufacturer of the station's network card"
        ::= { stationAssocEntry 2 }

    stationAssocIPAddress OBJECT-TYPE
        SYNTAX          DisplayString
        MAX-ACCESS      read-only
        STATUS          current
        DESCRIPTION
            "IP Address of the station"
        ::= { stationAssocEntry 3 }

    stationAssocNetbiosName OBJECT-TYPE
        SYNTAX          DisplayString
        MAX-ACCESS      read-only
        STATUS          current
        DESCRIPTION
            "Netbios name of the station"
        ::= { stationAssocEntry 4 }

    stationAssocIAP OBJECT-TYPE
        SYNTAX          DisplayString
        MAX-ACCESS      read-only
        STATUS          current
        DESCRIPTION
            "IAP station associated with"
        ::= { stationAssocEntry 5 }

    stationAssocSSID OBJECT-TYPE
        SYNTAX          DisplayString
        MAX-ACCESS      read-only
        STATUS          current
        DESCRIPTION
            "SSID station associated with"
        ::= { stationAssocEntry 6 }

    stationAssocVLAN OBJECT-TYPE
        SYNTAX          Integer32
        MAX-ACCESS      read-only
        STATUS          current
        DESCRIPTION
            "VLAN of the station"
        ::= { stationAssocEntry 7 }

    stationAssocRSSI OBJECT-TYPE
        SYNTAX          Integer32
        MAX-ACCESS      read-only
        STATUS          current
        DESCRIPTION
            "Station's RSSI (last packet received)"
        ::= { stationAssocEntry 8 }

    stationAssocTime OBJECT-TYPE
        SYNTAX          DisplayString
        MAX-ACCESS      read-only
        STATUS          current
        DESCRIPTION
            "Time (in D:H:M) station is associated"
        ::= { stationAssocEntry 9 }

    stationAssocTxRate OBJECT-TYPE
        SYNTAX          Integer32
        MAX-ACCESS      read-only
        STATUS          current
        DESCRIPTION
            "Tx rate of the station"
        ::= { stationAssocEntry 10 }

    stationAssocRxRate OBJECT-TYPE
        SYNTAX          Integer32
        MAX-ACCESS      read-only
        STATUS          current
        DESCRIPTION
            "Rx rate of the station"
        ::= { stationAssocEntry 11 }

    stationAssocRSSIa1 OBJECT-TYPE
        SYNTAX          Integer32
        MAX-ACCESS      read-only
        STATUS          current
        DESCRIPTION
            "Station's RSSI for last Probe Request on IAP a1"
        ::= { stationAssocEntry 12 }

    stationAssocRSSIa2 OBJECT-TYPE
        SYNTAX          Integer32
        MAX-ACCESS      read-only
        STATUS          current
        DESCRIPTION
            "Station's RSSI for last Probe Request on IAP a2"
        ::= { stationAssocEntry 13 }

    stationAssocRSSIa3 OBJECT-TYPE
        SYNTAX          Integer32
        MAX-ACCESS      read-only
        STATUS          current
        DESCRIPTION
            "Station's RSSI for last Probe Request on IAP a3"
        ::= { stationAssocEntry 14 }

    stationAssocRSSIa4 OBJECT-TYPE
        SYNTAX          Integer32
        MAX-ACCESS      read-only
        STATUS          current
        DESCRIPTION
            "Station's RSSI for last Probe Request on IAP a4"
        ::= { stationAssocEntry 15 }

    stationAssocRSSIa5 OBJECT-TYPE
        SYNTAX          Integer32
        MAX-ACCESS      read-only
        STATUS          current
        DESCRIPTION
            "Station's RSSI for last Probe Request on IAP a5"
        ::= { stationAssocEntry 16 }

    stationAssocRSSIa6 OBJECT-TYPE
        SYNTAX          Integer32
        MAX-ACCESS      read-only
        STATUS          current
        DESCRIPTION
            "Station's RSSI for last Probe Request on IAP a6"
        ::= { stationAssocEntry 17 }

    stationAssocRSSIa7 OBJECT-TYPE
        SYNTAX          Integer32
        MAX-ACCESS      read-only
        STATUS          current
        DESCRIPTION
            "Station's RSSI for last Probe Request on IAP a7"
        ::= { stationAssocEntry 18 }

    stationAssocRSSIa8 OBJECT-TYPE
        SYNTAX          Integer32
        MAX-ACCESS      read-only
        STATUS          current
        DESCRIPTION
            "Station's RSSI for last Probe Request on IAP a8"
        ::= { stationAssocEntry 19 }

    stationAssocRSSIa9 OBJECT-TYPE
        SYNTAX          Integer32
        MAX-ACCESS      read-only
        STATUS          current
        DESCRIPTION
            "Station's RSSI for last Probe Request on IAP a9"
        ::= { stationAssocEntry 20 }

    stationAssocRSSIa10 OBJECT-TYPE
        SYNTAX          Integer32
        MAX-ACCESS      read-only
        STATUS          current
        DESCRIPTION
            "Station's RSSI for last Probe Request on IAP a10"
        ::= { stationAssocEntry 21 }

    stationAssocRSSIa11 OBJECT-TYPE
        SYNTAX          Integer32
        MAX-ACCESS      read-only
        STATUS          current
        DESCRIPTION
            "Station's RSSI for last Probe Request on IAP a11"
        ::= { stationAssocEntry 22 }

    stationAssocRSSIa12 OBJECT-TYPE
        SYNTAX          Integer32
        MAX-ACCESS      read-only
        STATUS          current
        DESCRIPTION
            "Station's RSSI for last Probe Request on IAP a12"
        ::= { stationAssocEntry 23 }

    stationAssocRSSIabg1 OBJECT-TYPE
        SYNTAX          Integer32
        MAX-ACCESS      read-only
        STATUS          current
        DESCRIPTION
            "Station's RSSI for last Probe Request on IAP abg1"
        ::= { stationAssocEntry 24 }

    stationAssocRSSIabg2 OBJECT-TYPE
        SYNTAX          Integer32
        MAX-ACCESS      read-only
        STATUS          current
        DESCRIPTION
            "Station's RSSI for last Probe Request on IAP abg2"
        ::= { stationAssocEntry 25 }

    stationAssocRSSIabg3 OBJECT-TYPE
        SYNTAX          Integer32
        MAX-ACCESS      read-only
        STATUS          current
        DESCRIPTION
            "Station's RSSI for last Probe Request on IAP abg3"
        ::= { stationAssocEntry 26 }

    stationAssocRSSIabg4 OBJECT-TYPE
        SYNTAX          Integer32
        MAX-ACCESS      read-only
        STATUS          current
        DESCRIPTION
            "Station's RSSI for last Probe Request on IAP abg4"
        ::= { stationAssocEntry 27 }

    stationAssocEncType OBJECT-TYPE
        SYNTAX          INTEGER { none(0), wep(1), wpa(2), wpa2(3) }
        MAX-ACCESS      read-only
        STATUS          current
        DESCRIPTION
            "Station encryption type"
        ::= { stationAssocEntry 28 }

    stationAssocCipher OBJECT-TYPE
        SYNTAX          INTEGER { none(0), rc4(1), tkip(2), aes(3) }
        MAX-ACCESS      read-only
        STATUS          current
        DESCRIPTION
            "Cipher suite used by station"
        ::= { stationAssocEntry 29 }

    stationAssocKeyMgmt OBJECT-TYPE
        SYNTAX          INTEGER { none(0), eap(1), psk(2) }
        MAX-ACCESS      read-only
        STATUS          current
        DESCRIPTION
            "Key management algorithm used by station"
        ::= { stationAssocEntry 30 }

    stationAssocBand OBJECT-TYPE
        SYNTAX          INTEGER { dot11a(0),  dot11bg(1) }
        MAX-ACCESS      read-only
        STATUS          current
        DESCRIPTION
            "802.11 band station is on"
        ::= { stationAssocEntry 31 }

    stationAssocChannel OBJECT-TYPE
        SYNTAX          Integer32
        MAX-ACCESS      read-only
        STATUS          current
        DESCRIPTION
            "Channel station is on"
        ::= { stationAssocEntry 32 }

    stationAssocMediaType OBJECT-TYPE
        SYNTAX          INTEGER { dot11b(1), dot11bg(2), dot11abg(3), dot11a(4),
                                  dot11ab(5), dot11ag(6), dot11g(7), dot11n(8),
                                  dot11bn(9), dot11gn(10), dot11bgn(11), dot11an(12),
                                  dot11abn(13), dot11agn(14), dot11abgn(15),
                                  dot11anac(16), dot11abgnac(17)  }
        MAX-ACCESS      read-only
        STATUS          current
        DESCRIPTION
            "Station media type"
        ::= { stationAssocEntry 33 }

    stationAssocUserName OBJECT-TYPE
        SYNTAX          DisplayString
        MAX-ACCESS      read-only
        STATUS          current
        DESCRIPTION
            "Station user name"
        ::= { stationAssocEntry 34 }

    stationAssocTimeRSSIa1 OBJECT-TYPE
        SYNTAX          Counter32
        MAX-ACCESS      read-only
        STATUS          current
        DESCRIPTION
            "Station's elapsed time since last Probe Request on IAP a1 (milliseconds)"
        ::= { stationAssocEntry 35 }

    stationAssocTimeRSSIa2 OBJECT-TYPE
        SYNTAX          Counter32
        MAX-ACCESS      read-only
        STATUS          current
        DESCRIPTION
            "Station's elapsed time since last Probe Request on IAP a2 (milliseconds)"
        ::= { stationAssocEntry 36 }

    stationAssocTimeRSSIa3 OBJECT-TYPE
        SYNTAX          Counter32
        MAX-ACCESS      read-only
        STATUS          current
        DESCRIPTION
            "Station's elapsed time since last Probe Request on IAP a3 (milliseconds)"
        ::= { stationAssocEntry 37 }

    stationAssocTimeRSSIa4 OBJECT-TYPE
        SYNTAX          Counter32
        MAX-ACCESS      read-only
        STATUS          current
        DESCRIPTION
            "Station's elapsed time since last Probe Request on IAP a4 (milliseconds)"
        ::= { stationAssocEntry 38 }

    stationAssocTimeRSSIa5 OBJECT-TYPE
        SYNTAX          Counter32
        MAX-ACCESS      read-only
        STATUS          current
        DESCRIPTION
            "Station's elapsed time since last Probe Request on IAP a5 (milliseconds)"
        ::= { stationAssocEntry 39 }

    stationAssocTimeRSSIa6 OBJECT-TYPE
        SYNTAX          Counter32
        MAX-ACCESS      read-only
        STATUS          current
        DESCRIPTION
            "Station's elapsed time since last Probe Request on IAP a6 (milliseconds)"
        ::= { stationAssocEntry 40 }

    stationAssocTimeRSSIa7 OBJECT-TYPE
        SYNTAX          Counter32
        MAX-ACCESS      read-only
        STATUS          current
        DESCRIPTION
            "Station's elapsed time since last Probe Request on IAP a7 (milliseconds)"
        ::= { stationAssocEntry 41 }

    stationAssocTimeRSSIa8 OBJECT-TYPE
        SYNTAX          Counter32
        MAX-ACCESS      read-only
        STATUS          current
        DESCRIPTION
            "Station's elapsed time since last Probe Request on IAP a8 (milliseconds)"
        ::= { stationAssocEntry 42 }

    stationAssocTimeRSSIa9 OBJECT-TYPE
        SYNTAX          Counter32
        MAX-ACCESS      read-only
        STATUS          current
        DESCRIPTION
            "Station's elapsed time since last Probe Request on IAP a9 (milliseconds)"
        ::= { stationAssocEntry 43 }

    stationAssocTimeRSSIa10 OBJECT-TYPE
        SYNTAX          Counter32
        MAX-ACCESS      read-only
        STATUS          current
        DESCRIPTION
            "Station's elapsed time since last Probe Request on IAP a10 (milliseconds)"
        ::= { stationAssocEntry 44 }

    stationAssocTimeRSSIa11 OBJECT-TYPE
        SYNTAX          Counter32
        MAX-ACCESS      read-only
        STATUS          current
        DESCRIPTION
            "Station's elapsed time since last Probe Request on IAP a11 (milliseconds)"
        ::= { stationAssocEntry 45 }

    stationAssocTimeRSSIa12 OBJECT-TYPE
        SYNTAX          Counter32
        MAX-ACCESS      read-only
        STATUS          current
        DESCRIPTION
            "Station's elapsed time since last Probe Request on IAP a12 (milliseconds)"
        ::= { stationAssocEntry 46 }

    stationAssocTimeRSSIabg1 OBJECT-TYPE
        SYNTAX          Counter32
        MAX-ACCESS      read-only
        STATUS          current
        DESCRIPTION
            "Station's elapsed time since last Probe Request on IAP abg1 (milliseconds)"
        ::= { stationAssocEntry 47 }

    stationAssocTimeRSSIabg2 OBJECT-TYPE
        SYNTAX          Counter32
        MAX-ACCESS      read-only
        STATUS          current
        DESCRIPTION
            "Station's elapsed time since last Probe Request on IAP abg2 (milliseconds)"
        ::= { stationAssocEntry 48 }

    stationAssocTimeRSSIabg3 OBJECT-TYPE
        SYNTAX          Counter32
        MAX-ACCESS      read-only
        STATUS          current
        DESCRIPTION
            "Station's elapsed time since last Probe Request on IAP abg3 (milliseconds)"
        ::= { stationAssocEntry 49 }

    stationAssocTimeRSSIabg4 OBJECT-TYPE
        SYNTAX          Counter32
        MAX-ACCESS      read-only
        STATUS          current
        DESCRIPTION
            "Station's elapsed time since last Probe Request on IAP abg4 (milliseconds)"
        ::= { stationAssocEntry 50 }

    stationAssocHostname OBJECT-TYPE
        SYNTAX          DisplayString
        MAX-ACCESS      read-only
        STATUS          current
        DESCRIPTION
            "Station hostname"
        ::= { stationAssocEntry 51 }

    stationAssocDeviceType OBJECT-TYPE
        SYNTAX          DisplayString
        MAX-ACCESS      read-only
        STATUS          current
        DESCRIPTION
            "Station device type"
        ::= { stationAssocEntry 52 }

    stationAssocDeviceClass OBJECT-TYPE
        SYNTAX          DisplayString
        MAX-ACCESS      read-only
        STATUS          current
        DESCRIPTION
            "Station device class"
        ::= { stationAssocEntry 53 }

    stationAssocUserAgent OBJECT-TYPE
        SYNTAX          DisplayString
        MAX-ACCESS      read-only
        STATUS          current
        DESCRIPTION
            "User-agent string"
        ::= { stationAssocEntry 54 }

    stationAssocDeviceSource OBJECT-TYPE
        SYNTAX          INTEGER { none(0), manufacturer(1), netbios-name(2),
                                  dhcp-hostname(3), user-agent-string(4),
                                  internal-rules(5), external-rules(6), cache(7) }
        MAX-ACCESS      read-only
        STATUS          current
        DESCRIPTION
            "Station device source"
        ::= { stationAssocEntry 55 }

    stationAssocDeviceSourceIndex OBJECT-TYPE
        SYNTAX          Integer32
        MAX-ACCESS      read-only
        STATUS          current
        DESCRIPTION
            "Station device source index"
        ::= { stationAssocEntry 56 }

    stationUnassocTable OBJECT-TYPE
        SYNTAX          SEQUENCE OF StationUnassocEntry
        MAX-ACCESS      not-accessible
        STATUS          current
        DESCRIPTION
            "Table of unassociated stations (indexed by station MAC address)"
        ::= { stations 5 }

    stationUnassocEntry OBJECT-TYPE
        SYNTAX          StationUnassocEntry
        MAX-ACCESS      not-accessible
        STATUS          current
        DESCRIPTION
            "Table entry for unassociated station"
        INDEX       { stationUnassocMACAddress }
        ::= { stationUnassocTable 1 }

    StationUnassocEntry ::= SEQUENCE {
        stationUnassocMACAddress        DisplayString,
        stationUnassocManufacturer      DisplayString,
        stationUnassocNetbiosName       DisplayString,
        stationUnassocMediaType         INTEGER,
        stationUnassocTxRate            Integer32,
        stationUnassocRxRate            Integer32,
        stationUnassocRSSI              Integer32,
        stationUnassocTime              Counter32,
        stationUnassocRSSIa1            Integer32,
        stationUnassocRSSIa2            Integer32,
        stationUnassocRSSIa3            Integer32,
        stationUnassocRSSIa4            Integer32,
        stationUnassocRSSIa5            Integer32,
        stationUnassocRSSIa6            Integer32,
        stationUnassocRSSIa7            Integer32,
        stationUnassocRSSIa8            Integer32,
        stationUnassocRSSIa9            Integer32,
        stationUnassocRSSIa10           Integer32,
        stationUnassocRSSIa11           Integer32,
        stationUnassocRSSIa12           Integer32,
        stationUnassocRSSIabg1          Integer32,
        stationUnassocRSSIabg2          Integer32,
        stationUnassocRSSIabg3          Integer32,
        stationUnassocRSSIabg4          Integer32,
        stationUnassocTimeRSSIa1        Counter32,
        stationUnassocTimeRSSIa2        Counter32,
        stationUnassocTimeRSSIa3        Counter32,
        stationUnassocTimeRSSIa4        Counter32,
        stationUnassocTimeRSSIa5        Counter32,
        stationUnassocTimeRSSIa6        Counter32,
        stationUnassocTimeRSSIa7        Counter32,
        stationUnassocTimeRSSIa8        Counter32,
        stationUnassocTimeRSSIa9        Counter32,
        stationUnassocTimeRSSIa10       Counter32,
        stationUnassocTimeRSSIa11       Counter32,
        stationUnassocTimeRSSIa12       Counter32,
        stationUnassocTimeRSSIabg1      Counter32,
        stationUnassocTimeRSSIabg2      Counter32,
        stationUnassocTimeRSSIabg3      Counter32,
        stationUnassocTimeRSSIabg4      Counter32
    }

    stationUnassocMACAddress OBJECT-TYPE
        SYNTAX          DisplayString
        MAX-ACCESS      read-only
        STATUS          current
        DESCRIPTION
            "MAC address of the station"
        ::= { stationUnassocEntry 1 }

    stationUnassocManufacturer OBJECT-TYPE
        SYNTAX          DisplayString
        MAX-ACCESS      read-only
        STATUS          current
        DESCRIPTION
            "Manufacturer of the station's network card"
        ::= { stationUnassocEntry 2 }

    stationUnassocNetbiosName OBJECT-TYPE
        SYNTAX          DisplayString
        MAX-ACCESS      read-only
        STATUS          current
        DESCRIPTION
            "Netbios name of the station"
        ::= { stationUnassocEntry 3 }

    stationUnassocMediaType OBJECT-TYPE
        SYNTAX          INTEGER { dot11b(1), dot11bg(2), dot11abg(3), dot11a(4),
                                  dot11ab(5), dot11ag(6), dot11g(7), dot11n(8),
                                  dot11bn(9), dot11gn(10), dot11bgn(11), dot11an(12),
                                  dot11abn(13), dot11agn(14), dot11abgn(15),
                                  dot11anac(16), dot11abgnac(17)  }
        MAX-ACCESS      read-only
        STATUS          current
        DESCRIPTION
            "Station media type"
        ::= { stationUnassocEntry 4 }

    stationUnassocTxRate OBJECT-TYPE
        SYNTAX          Integer32
        MAX-ACCESS      read-only
        STATUS          current
        DESCRIPTION
            "Tx rate of the station"
        ::= { stationUnassocEntry 5 }

    stationUnassocRxRate OBJECT-TYPE
        SYNTAX          Integer32
        MAX-ACCESS      read-only
        STATUS          current
        DESCRIPTION
            "Rx rate of the station"
        ::= { stationUnassocEntry 6 }

    stationUnassocRSSI OBJECT-TYPE
        SYNTAX          Integer32
        MAX-ACCESS      read-only
        STATUS          current
        DESCRIPTION
            "Station's RSSI (last packet received)"
        ::= { stationUnassocEntry 7 }

    stationUnassocTime OBJECT-TYPE
        SYNTAX          Counter32
        MAX-ACCESS      read-only
        STATUS          current
        DESCRIPTION
            "Time (in seconds) since Rx"
        ::= { stationUnassocEntry 8 }

    stationUnassocRSSIa1 OBJECT-TYPE
        SYNTAX          Integer32
        MAX-ACCESS      read-only
        STATUS          current
        DESCRIPTION
            "Station's RSSI for last Probe Request on IAP a1"
        ::= { stationUnassocEntry 9 }

    stationUnassocRSSIa2 OBJECT-TYPE
        SYNTAX          Integer32
        MAX-ACCESS      read-only
        STATUS          current
        DESCRIPTION
            "Station's RSSI for last Probe Request on IAP a2"
        ::= { stationUnassocEntry 10 }

    stationUnassocRSSIa3 OBJECT-TYPE
        SYNTAX          Integer32
        MAX-ACCESS      read-only
        STATUS          current
        DESCRIPTION
            "Station's RSSI for last Probe Request on IAP a3"
        ::= { stationUnassocEntry 11 }

    stationUnassocRSSIa4 OBJECT-TYPE
        SYNTAX          Integer32
        MAX-ACCESS      read-only
        STATUS          current
        DESCRIPTION
            "Station's RSSI for last Probe Request on IAP a4"
        ::= { stationUnassocEntry 12 }

    stationUnassocRSSIa5 OBJECT-TYPE
        SYNTAX          Integer32
        MAX-ACCESS      read-only
        STATUS          current
        DESCRIPTION
            "Station's RSSI for last Probe Request on IAP a5"
        ::= { stationUnassocEntry 13 }

    stationUnassocRSSIa6 OBJECT-TYPE
        SYNTAX          Integer32
        MAX-ACCESS      read-only
        STATUS          current
        DESCRIPTION
            "Station's RSSI for last Probe Request on IAP a6"
        ::= { stationUnassocEntry 14 }

    stationUnassocRSSIa7 OBJECT-TYPE
        SYNTAX          Integer32
        MAX-ACCESS      read-only
        STATUS          current
        DESCRIPTION
            "Station's RSSI for last Probe Request on IAP a7"
        ::= { stationUnassocEntry 15 }

    stationUnassocRSSIa8 OBJECT-TYPE
        SYNTAX          Integer32
        MAX-ACCESS      read-only
        STATUS          current
        DESCRIPTION
            "Station's RSSI for last Probe Request on IAP a8"
        ::= { stationUnassocEntry 16 }

    stationUnassocRSSIa9 OBJECT-TYPE
        SYNTAX          Integer32
        MAX-ACCESS      read-only
        STATUS          current
        DESCRIPTION
            "Station's RSSI for last Probe Request on IAP a9"
        ::= { stationUnassocEntry 17 }

    stationUnassocRSSIa10 OBJECT-TYPE
        SYNTAX          Integer32
        MAX-ACCESS      read-only
        STATUS          current
        DESCRIPTION
            "Station's RSSI for last Probe Request on IAP a10"
        ::= { stationUnassocEntry 18 }

    stationUnassocRSSIa11 OBJECT-TYPE
        SYNTAX          Integer32
        MAX-ACCESS      read-only
        STATUS          current
        DESCRIPTION
            "Station's RSSI for last Probe Request on IAP a11"
        ::= { stationUnassocEntry 19 }

    stationUnassocRSSIa12 OBJECT-TYPE
        SYNTAX          Integer32
        MAX-ACCESS      read-only
        STATUS          current
        DESCRIPTION
            "Station's RSSI for last Probe Request on IAP a12"
        ::= { stationUnassocEntry 20 }

    stationUnassocRSSIabg1 OBJECT-TYPE
        SYNTAX          Integer32
        MAX-ACCESS      read-only
        STATUS          current
        DESCRIPTION
            "Station's RSSI for last Probe Request on IAP abg1"
        ::= { stationUnassocEntry 21 }

    stationUnassocRSSIabg2 OBJECT-TYPE
        SYNTAX          Integer32
        MAX-ACCESS      read-only
        STATUS          current
        DESCRIPTION
            "Station's RSSI for last Probe Request on IAP abg2"
        ::= { stationUnassocEntry 22 }

    stationUnassocRSSIabg3 OBJECT-TYPE
        SYNTAX          Integer32
        MAX-ACCESS      read-only
        STATUS          current
        DESCRIPTION
            "Station's RSSI for last Probe Request on IAP abg3"
        ::= { stationUnassocEntry 23 }

    stationUnassocRSSIabg4 OBJECT-TYPE
        SYNTAX          Integer32
        MAX-ACCESS      read-only
        STATUS          current
        DESCRIPTION
            "Station's RSSI for last Probe Request on IAP abg4"
        ::= { stationUnassocEntry 24 }

    stationUnassocTimeRSSIa1 OBJECT-TYPE
        SYNTAX          Counter32
        MAX-ACCESS      read-only
        STATUS          current
        DESCRIPTION
            "Station's elapsed time since last Probe Request on IAP a1 (milliseconds)"
        ::= { stationUnassocEntry 25 }

    stationUnassocTimeRSSIa2 OBJECT-TYPE
        SYNTAX          Counter32
        MAX-ACCESS      read-only
        STATUS          current
        DESCRIPTION
            "Station's elapsed time since last Probe Request on IAP a2 (milliseconds)"
        ::= { stationUnassocEntry 26 }

    stationUnassocTimeRSSIa3 OBJECT-TYPE
        SYNTAX          Counter32
        MAX-ACCESS      read-only
        STATUS          current
        DESCRIPTION
            "Station's elapsed time since last Probe Request on IAP a3 (milliseconds)"
        ::= { stationUnassocEntry 27 }

    stationUnassocTimeRSSIa4 OBJECT-TYPE
        SYNTAX          Counter32
        MAX-ACCESS      read-only
        STATUS          current
        DESCRIPTION
            "Station's elapsed time since last Probe Request on IAP a4 (milliseconds)"
        ::= { stationUnassocEntry 28 }

    stationUnassocTimeRSSIa5 OBJECT-TYPE
        SYNTAX          Counter32
        MAX-ACCESS      read-only
        STATUS          current
        DESCRIPTION
            "Station's elapsed time since last Probe Request on IAP a5 (milliseconds)"
        ::= { stationUnassocEntry 29 }

    stationUnassocTimeRSSIa6 OBJECT-TYPE
        SYNTAX          Counter32
        MAX-ACCESS      read-only
        STATUS          current
        DESCRIPTION
            "Station's elapsed time since last Probe Request on IAP a6 (milliseconds)"
        ::= { stationUnassocEntry 30 }

    stationUnassocTimeRSSIa7 OBJECT-TYPE
        SYNTAX          Counter32
        MAX-ACCESS      read-only
        STATUS          current
        DESCRIPTION
            "Station's elapsed time since last Probe Request on IAP a7 (milliseconds)"
        ::= { stationUnassocEntry 31 }

    stationUnassocTimeRSSIa8 OBJECT-TYPE
        SYNTAX          Counter32
        MAX-ACCESS      read-only
        STATUS          current
        DESCRIPTION
            "Station's elapsed time since last Probe Request on IAP a8 (milliseconds)"
        ::= { stationUnassocEntry 32 }

    stationUnassocTimeRSSIa9 OBJECT-TYPE
        SYNTAX          Counter32
        MAX-ACCESS      read-only
        STATUS          current
        DESCRIPTION
            "Station's elapsed time since last Probe Request on IAP a9 (milliseconds)"
        ::= { stationUnassocEntry 33 }

    stationUnassocTimeRSSIa10 OBJECT-TYPE
        SYNTAX          Counter32
        MAX-ACCESS      read-only
        STATUS          current
        DESCRIPTION
            "Station's elapsed time since last Probe Request on IAP a10 (milliseconds)"
        ::= { stationUnassocEntry 34 }

    stationUnassocTimeRSSIa11 OBJECT-TYPE
        SYNTAX          Counter32
        MAX-ACCESS      read-only
        STATUS          current
        DESCRIPTION
            "Station's elapsed time since last Probe Request on IAP a11 (milliseconds)"
        ::= { stationUnassocEntry 35 }

    stationUnassocTimeRSSIa12 OBJECT-TYPE
        SYNTAX          Counter32
        MAX-ACCESS      read-only
        STATUS          current
        DESCRIPTION
            "Station's elapsed time since last Probe Request on IAP a12 (milliseconds)"
        ::= { stationUnassocEntry 36 }

    stationUnassocTimeRSSIabg1 OBJECT-TYPE
        SYNTAX          Counter32
        MAX-ACCESS      read-only
        STATUS          current
        DESCRIPTION
            "Station's elapsed time since last Probe Request on IAP abg1 (milliseconds)"
        ::= { stationUnassocEntry 37 }

    stationUnassocTimeRSSIabg2 OBJECT-TYPE
        SYNTAX          Counter32
        MAX-ACCESS      read-only
        STATUS          current
        DESCRIPTION
            "Station's elapsed time since last Probe Request on IAP abg2 (milliseconds)"
        ::= { stationUnassocEntry 38 }

    stationUnassocTimeRSSIabg3 OBJECT-TYPE
        SYNTAX          Counter32
        MAX-ACCESS      read-only
        STATUS          current
        DESCRIPTION
            "Station's elapsed time since last Probe Request on IAP abg3 (milliseconds)"
        ::= { stationUnassocEntry 39 }

    stationUnassocTimeRSSIabg4 OBJECT-TYPE
        SYNTAX          Counter32
        MAX-ACCESS      read-only
        STATUS          current
        DESCRIPTION
            "Station's elapsed time since last Probe Request on IAP abg4 (milliseconds)"
        ::= { stationUnassocEntry 40 }

    stationAssurance    OBJECT IDENTIFIER ::= { stations 6 }

--
-- STATION ASSURANCE
--

    stationAssuranceEnable OBJECT-TYPE
        SYNTAX          INTEGER { disable(0), enable(1) }
        MAX-ACCESS      read-write
        STATUS          current
        DESCRIPTION
            "Enable/disable station assurance"
        ::= { stationAssurance 1 }

    stationAssurancePeriod OBJECT-TYPE
        SYNTAX          Integer32(60..9999)
        MAX-ACCESS      read-write
        STATUS          current
        DESCRIPTION
            "Station assurance check period (in seconds)"
        ::= { stationAssurance 2 }

    stationAssuranceAssocTime OBJECT-TYPE
        SYNTAX          Integer32(1..999)
        MAX-ACCESS      read-write
        STATUS          current
        DESCRIPTION
            "Minimum average associated time (in seconds)"
        ::= { stationAssurance 3 }

    stationAssuranceAuthFailures OBJECT-TYPE
        SYNTAX          Integer32(1..99)
        MAX-ACCESS      read-write
        STATUS          current
        DESCRIPTION
            "Maximum number of authentication failures"
        ::= { stationAssurance 4 }

    stationAssuranceErrorRate OBJECT-TYPE
        SYNTAX          Integer32(1..99)
        MAX-ACCESS      read-write
        STATUS          current
        DESCRIPTION
            "Maximum packet error rate (as a percentage)"
        ::= { stationAssurance 5 }

    stationAssuranceRetryRate OBJECT-TYPE
        SYNTAX          Integer32(1..99)
        MAX-ACCESS      read-write
        STATUS          current
        DESCRIPTION
            "Maximum packet retry rate (as a percentage)"
        ::= { stationAssurance 6 }

    stationAssuranceDataRate OBJECT-TYPE
        SYNTAX          Integer32(1..99)
        MAX-ACCESS      read-write
        STATUS          current
        DESCRIPTION
            "Minimum packet data rate (in Mbps)"
        ::= { stationAssurance 7 }

    stationAssuranceRSSI OBJECT-TYPE
        SYNTAX          Integer32(-90..-50)
        MAX-ACCESS      read-write
        STATUS          current
        DESCRIPTION
            "Minimum received signal strength (in dB)"
        ::= { stationAssurance 8 }

    stationAssuranceSNR OBJECT-TYPE
        SYNTAX          Integer32(1..25)
        MAX-ACCESS      read-write
        STATUS          current
        DESCRIPTION
            "Minimum signal to noise ratio (in dB)"
        ::= { stationAssurance 9 }

    stationAssuranceDistance OBJECT-TYPE
        SYNTAX          Integer32(1..9999)
        MAX-ACCESS      read-write
        STATUS          current
        DESCRIPTION
            "Maximum distance from array (in feet)"
        ::= { stationAssurance 10 }

    stationAssuranceTable OBJECT-TYPE
        SYNTAX          SEQUENCE OF StationAssuranceEntry
        MAX-ACCESS      not-accessible
        STATUS          current
        DESCRIPTION
            "Station assurance table"
        ::= { stationAssurance 11 }

    stationAssuranceEntry OBJECT-TYPE
        SYNTAX          StationAssuranceEntry
        MAX-ACCESS      not-accessible
        STATUS          current
        DESCRIPTION
            "Station assurance table entry"
        INDEX       { staAssuranceIndex }
        ::= { stationAssuranceTable 1 }

    StationAssuranceEntry ::= SEQUENCE {
        staAssuranceIndex                   Integer32,
        staAssuranceMACAddress              DisplayString,
        staAssuranceIPAddress               DisplayString,
        staAssuranceNetbiosName             DisplayString,
        staAssuranceManufacturer            DisplayString,
        staAssuranceTime                    DisplayString,
        staAssuranceTimestamp               Counter32,
        staAssuranceAssocTime               Integer32,
        staAssuranceAuthFailures            Integer32,
        staAssuranceErrorRate               Integer32,
        staAssuranceRetryRate               Integer32,
        staAssuranceDataRate                Integer32,
        staAssuranceRSSI                    Integer32,
        staAssuranceSNR                     Integer32,
        staAssuranceDistance                Integer32,
        staAssuranceDeviceType              DisplayString,
        staAssuranceDeviceClass             DisplayString,
        staAssuranceActiveAlarmTimestamp    Counter32,
        staAssuranceActiveAlarmType         INTEGER,
        staAssuranceAssocTimeTimestamp      Counter32,
        staAssuranceAuthFailuresTimestamp   Counter32,
        staAssuranceErrorRateTimestamp      Counter32,
        staAssuranceRetryRateTimestamp      Counter32,
        staAssuranceDataRateTimestamp       Counter32,
        staAssuranceRSSITimestamp           Counter32,
        staAssuranceSNRTimestamp            Counter32,
        staAssuranceDistanceTimestamp       Counter32,
        staAssuranceAssocTimeActive         INTEGER,
        staAssuranceAuthFailuresActive      INTEGER,
        staAssuranceErrorRateActive         INTEGER,
        staAssuranceRetryRateActive         INTEGER,
        staAssuranceDataRateActive          INTEGER,
        staAssuranceRSSIActive              INTEGER,
        staAssuranceSNRActive               INTEGER,
        staAssuranceDistanceActive          INTEGER,
        staAssuranceAlarmType               INTEGER
    }

    staAssuranceIndex OBJECT-TYPE
        SYNTAX          Integer32
        MAX-ACCESS      not-accessible
        STATUS          current
        DESCRIPTION
            "Station assurance index"
        ::= { stationAssuranceEntry 1 }

    staAssuranceMACAddress OBJECT-TYPE
        SYNTAX          DisplayString
        MAX-ACCESS      read-only
        STATUS          current
        DESCRIPTION
            "Station MAC address"
        ::= { stationAssuranceEntry 2 }

    staAssuranceIPAddress OBJECT-TYPE
        SYNTAX          DisplayString
        MAX-ACCESS      read-only
        STATUS          current
        DESCRIPTION
            "Station IP Address"
        ::= { stationAssuranceEntry 3 }

    staAssuranceNetbiosName OBJECT-TYPE
        SYNTAX          DisplayString
        MAX-ACCESS      read-only
        STATUS          current
        DESCRIPTION
            "Station netbios name"
        ::= { stationAssuranceEntry 4 }

    staAssuranceManufacturer OBJECT-TYPE
        SYNTAX          DisplayString
        MAX-ACCESS      read-only
        STATUS          current
        DESCRIPTION
            "Manufacturer of the station's network card"
        ::= { stationAssuranceEntry 5 }

    staAssuranceTime OBJECT-TYPE
        SYNTAX          DisplayString
        MAX-ACCESS      read-only
        STATUS          current
        DESCRIPTION
            "Last alarm time"
        ::= { stationAssuranceEntry 6 }

    staAssuranceTimestamp OBJECT-TYPE
        SYNTAX          Counter32
        MAX-ACCESS      read-only
        STATUS          current
        DESCRIPTION
            "Last alarm time (in seconds)"
        ::= { stationAssuranceEntry 7 }

    staAssuranceAssocTime OBJECT-TYPE
        SYNTAX          Integer32
        MAX-ACCESS      read-only
        STATUS          current
        DESCRIPTION
            "Associated time"
        ::= { stationAssuranceEntry 8 }

    staAssuranceAuthFailures OBJECT-TYPE
        SYNTAX          Integer32
        MAX-ACCESS      read-only
        STATUS          current
        DESCRIPTION
            "Number of authentication failures"
        ::= { stationAssuranceEntry 9 }

    staAssuranceErrorRate OBJECT-TYPE
        SYNTAX          Integer32
        MAX-ACCESS      read-only
        STATUS          current
        DESCRIPTION
            "Packet error rate"
        ::= { stationAssuranceEntry 10 }

    staAssuranceRetryRate OBJECT-TYPE
        SYNTAX          Integer32
        MAX-ACCESS      read-only
        STATUS          current
        DESCRIPTION
            "Packet retry rate"
        ::= { stationAssuranceEntry 11 }

    staAssuranceDataRate OBJECT-TYPE
        SYNTAX          Integer32
        MAX-ACCESS      read-only
        STATUS          current
        DESCRIPTION
            "Packet data rate"
        ::= { stationAssuranceEntry 12 }

    staAssuranceRSSI OBJECT-TYPE
        SYNTAX          Integer32
        MAX-ACCESS      read-only
        STATUS          current
        DESCRIPTION
            "Received signal strength"
        ::= { stationAssuranceEntry 13 }

    staAssuranceSNR OBJECT-TYPE
        SYNTAX          Integer32
        MAX-ACCESS      read-only
        STATUS          current
        DESCRIPTION
            "Signal to noise ratio"
        ::= { stationAssuranceEntry 14 }

    staAssuranceDistance OBJECT-TYPE
        SYNTAX          Integer32
        MAX-ACCESS      read-only
        STATUS          current
        DESCRIPTION
            "Distance from array"
        ::= { stationAssuranceEntry 15 }

    staAssuranceDeviceType OBJECT-TYPE
        SYNTAX          DisplayString
        MAX-ACCESS      read-only
        STATUS          current
        DESCRIPTION
            "Station device type"
        ::= { stationAssuranceEntry 16 }

    staAssuranceDeviceClass OBJECT-TYPE
        SYNTAX          DisplayString
        MAX-ACCESS      read-only
        STATUS          current
        DESCRIPTION
            "Station device class"
        ::= { stationAssuranceEntry 17 }

    staAssuranceActiveAlarmTimestamp OBJECT-TYPE
        SYNTAX          Counter32
        MAX-ACCESS      read-only
        STATUS          current
        DESCRIPTION
            "Last active alarm time (in seconds)"
        ::= { stationAssuranceEntry 18 }

    staAssuranceActiveAlarmType OBJECT-TYPE
        SYNTAX          INTEGER { none(0), assoc-time(1), auth-fails(2),
                                  error-rate(3), retry-rate(4), data-rate(5),
                                  rssi(6), snr(7), distance(8) }
        MAX-ACCESS      read-only
        STATUS          current
        DESCRIPTION
            "Last active alarm type"
        ::= { stationAssuranceEntry 19 }

    staAssuranceAssocTimeTimestamp OBJECT-TYPE
        SYNTAX          Counter32
        MAX-ACCESS      read-only
        STATUS          current
        DESCRIPTION
            "Last associated time alarm time (in seconds)"
        ::= { stationAssuranceEntry 20 }

    staAssuranceAuthFailuresTimestamp OBJECT-TYPE
        SYNTAX          Counter32
        MAX-ACCESS      read-only
        STATUS          current
        DESCRIPTION
            "Last authentication failures alarm time (in seconds)"
        ::= { stationAssuranceEntry 21 }

    staAssuranceErrorRateTimestamp OBJECT-TYPE
        SYNTAX          Counter32
        MAX-ACCESS      read-only
        STATUS          current
        DESCRIPTION
            "Last packet error rate alarm time (in seconds)"
        ::= { stationAssuranceEntry 22 }

    staAssuranceRetryRateTimestamp OBJECT-TYPE
        SYNTAX          Counter32
        MAX-ACCESS      read-only
        STATUS          current
        DESCRIPTION
            "Last packet retry rate alarm time (in seconds)"
        ::= { stationAssuranceEntry 23 }

    staAssuranceDataRateTimestamp OBJECT-TYPE
        SYNTAX          Counter32
        MAX-ACCESS      read-only
        STATUS          current
        DESCRIPTION
            "Last packet data rate alarm time (in seconds)"
        ::= { stationAssuranceEntry 24 }

    staAssuranceRSSITimestamp OBJECT-TYPE
        SYNTAX          Counter32
        MAX-ACCESS      read-only
        STATUS          current
        DESCRIPTION
            "Last RSSI alarm time (in seconds)"
        ::= { stationAssuranceEntry 25 }

    staAssuranceSNRTimestamp OBJECT-TYPE
        SYNTAX          Counter32
        MAX-ACCESS      read-only
        STATUS          current
        DESCRIPTION
            "Last SNR alarm time (in seconds)"
        ::= { stationAssuranceEntry 26 }

    staAssuranceDistanceTimestamp OBJECT-TYPE
        SYNTAX          Counter32
        MAX-ACCESS      read-only
        STATUS          current
        DESCRIPTION
            "Last distance alarm time (in seconds)"
        ::= { stationAssuranceEntry 27 }

    staAssuranceAssocTimeActive OBJECT-TYPE
        SYNTAX          INTEGER { inactive(0), active(1) }
        MAX-ACCESS      read-only
        STATUS          current
        DESCRIPTION
            "Flag indicating whether associated time alarm is currently active"
        ::= { stationAssuranceEntry 28 }

    staAssuranceAuthFailuresActive OBJECT-TYPE
        SYNTAX          INTEGER { inactive(0), active(1) }
        MAX-ACCESS      read-only
        STATUS          current
        DESCRIPTION
            "Flag indicating whether authentication failures alarm is currently active"
        ::= { stationAssuranceEntry 29 }

    staAssuranceErrorRateActive OBJECT-TYPE
        SYNTAX          INTEGER { inactive(0), active(1) }
        MAX-ACCESS      read-only
        STATUS          current
        DESCRIPTION
            "Flag indicating whether error rate alarm is currently active"
        ::= { stationAssuranceEntry 30 }

    staAssuranceRetryRateActive OBJECT-TYPE
        SYNTAX          INTEGER { inactive(0), active(1) }
        MAX-ACCESS      read-only
        STATUS          current
        DESCRIPTION
            "Flag indicating whether retry rate alarm is currently active"
        ::= { stationAssuranceEntry 31 }

    staAssuranceDataRateActive OBJECT-TYPE
        SYNTAX          INTEGER { inactive(0), active(1) }
        MAX-ACCESS      read-only
        STATUS          current
        DESCRIPTION
            "Flag indicating whether data rate alarm is currently active"
        ::= { stationAssuranceEntry 32 }

    staAssuranceRSSIActive OBJECT-TYPE
        SYNTAX          INTEGER { inactive(0), active(1) }
        MAX-ACCESS      read-only
        STATUS          current
        DESCRIPTION
            "Flag indicating whether RSSI alarm is currently active"
        ::= { stationAssuranceEntry 33 }

    staAssuranceSNRActive OBJECT-TYPE
        SYNTAX          INTEGER { inactive(0), active(1) }
        MAX-ACCESS      read-only
        STATUS          current
        DESCRIPTION
            "Flag indicating whether SNR alarm is currently active"
        ::= { stationAssuranceEntry 34 }

    staAssuranceDistanceActive OBJECT-TYPE
        SYNTAX          INTEGER { inactive(0), active(1) }
        MAX-ACCESS      read-only
        STATUS          current
        DESCRIPTION
            "Flag indicating whether distance alarm is currently active"
        ::= { stationAssuranceEntry 35 }

    staAssuranceAlarmType OBJECT-TYPE
        SYNTAX          INTEGER { none(0), assoc-time(1), auth-fails(2),
                                  error-rate(3), retry-rate(4), data-rate(5),
                                  rssi(6), snr(7), distance(8) }
        MAX-ACCESS      read-only
        STATUS          current
        DESCRIPTION
            "Last alarm type"
        ::= { stationAssuranceEntry 36 }

    stationAssurTable OBJECT-TYPE
        SYNTAX          SEQUENCE OF StationAssurEntry
        MAX-ACCESS      not-accessible
        STATUS          current
        DESCRIPTION
            "Station assurance table (indexed by station MAC address)"
        ::= { stationAssurance 12 }

    stationAssurEntry OBJECT-TYPE
        SYNTAX          StationAssurEntry
        MAX-ACCESS      not-accessible
        STATUS          current
        DESCRIPTION
            "Station assurance table entry"
        INDEX       { staAssurMACAddress }
        ::= { stationAssurTable 1 }

    StationAssurEntry ::= SEQUENCE {
        staAssurMACAddress                  DisplayString,
        staAssurIPAddress                   DisplayString,
        staAssurNetbiosName                 DisplayString,
        staAssurManufacturer                DisplayString,
        staAssurTime                        DisplayString,
        staAssurTimestamp                   Counter32,
        staAssurAssocTime                   Integer32,
        staAssurAuthFailures                Integer32,
        staAssurErrorRate                   Integer32,
        staAssurRetryRate                   Integer32,
        staAssurDataRate                    Integer32,
        staAssurRSSI                        Integer32,
        staAssurSNR                         Integer32,
        staAssurDistance                    Integer32,
        staAssurDeviceType                  DisplayString,
        staAssurDeviceClass                 DisplayString,
        staAssurActiveAlarmTimestamp        Counter32,
        staAssurActiveAlarmType             INTEGER,
        staAssurAssocTimeTimestamp          Counter32,
        staAssurAuthFailuresTimestamp       Counter32,
        staAssurErrorRateTimestamp          Counter32,
        staAssurRetryRateTimestamp          Counter32,
        staAssurDataRateTimestamp           Counter32,
        staAssurRSSITimestamp               Counter32,
        staAssurSNRTimestamp                Counter32,
        staAssurDistanceTimestamp           Counter32,
        staAssurAssocTimeActive             INTEGER,
        staAssurAuthFailuresActive          INTEGER,
        staAssurErrorRateActive             INTEGER,
        staAssurRetryRateActive             INTEGER,
        staAssurDataRateActive              INTEGER,
        staAssurRSSIActive                  INTEGER,
        staAssurSNRActive                   INTEGER,
        staAssurDistanceActive              INTEGER,
        staAssurAlarmType                   INTEGER
    }

    staAssurMACAddress OBJECT-TYPE
        SYNTAX          DisplayString
        MAX-ACCESS      read-only
        STATUS          current
        DESCRIPTION
            "Station MAC address"
        ::= { stationAssurEntry 1 }

    staAssurIPAddress OBJECT-TYPE
        SYNTAX          DisplayString
        MAX-ACCESS      read-only
        STATUS          current
        DESCRIPTION
            "Station IP Address"
        ::= { stationAssurEntry 2 }

    staAssurNetbiosName OBJECT-TYPE
        SYNTAX          DisplayString
        MAX-ACCESS      read-only
        STATUS          current
        DESCRIPTION
            "Station netbios name"
        ::= { stationAssurEntry 3 }

    staAssurManufacturer OBJECT-TYPE
        SYNTAX          DisplayString
        MAX-ACCESS      read-only
        STATUS          current
        DESCRIPTION
            "Manufacturer of the station's network card"
        ::= { stationAssurEntry 4 }

    staAssurTime OBJECT-TYPE
        SYNTAX          DisplayString
        MAX-ACCESS      read-only
        STATUS          current
        DESCRIPTION
            "Last alarm time"
        ::= { stationAssurEntry 5 }

    staAssurTimestamp OBJECT-TYPE
        SYNTAX          Counter32
        MAX-ACCESS      read-only
        STATUS          current
        DESCRIPTION
            "Last alarm time (in seconds)"
        ::= { stationAssurEntry 6 }

    staAssurAssocTime OBJECT-TYPE
        SYNTAX          Integer32
        MAX-ACCESS      read-only
        STATUS          current
        DESCRIPTION
            "Associated time"
        ::= { stationAssurEntry 7 }

    staAssurAuthFailures OBJECT-TYPE
        SYNTAX          Integer32
        MAX-ACCESS      read-only
        STATUS          current
        DESCRIPTION
            "Number of authentication failures"
        ::= { stationAssurEntry 8 }

    staAssurErrorRate OBJECT-TYPE
        SYNTAX          Integer32
        MAX-ACCESS      read-only
        STATUS          current
        DESCRIPTION
            "Packet error rate"
        ::= { stationAssurEntry 9 }

    staAssurRetryRate OBJECT-TYPE
        SYNTAX          Integer32
        MAX-ACCESS      read-only
        STATUS          current
        DESCRIPTION
            "Packet retry rate"
        ::= { stationAssurEntry 10 }

    staAssurDataRate OBJECT-TYPE
        SYNTAX          Integer32
        MAX-ACCESS      read-only
        STATUS          current
        DESCRIPTION
            "Packet data rate"
        ::= { stationAssurEntry 11 }

    staAssurRSSI OBJECT-TYPE
        SYNTAX          Integer32
        MAX-ACCESS      read-only
        STATUS          current
        DESCRIPTION
            "Received signal strength"
        ::= { stationAssurEntry 12 }

    staAssurSNR OBJECT-TYPE
        SYNTAX          Integer32
        MAX-ACCESS      read-only
        STATUS          current
        DESCRIPTION
            "Signal to noise ratio"
        ::= { stationAssurEntry 13 }

    staAssurDistance OBJECT-TYPE
        SYNTAX          Integer32
        MAX-ACCESS      read-only
        STATUS          current
        DESCRIPTION
            "Distance from array"
        ::= { stationAssurEntry 14 }

    staAssurDeviceType OBJECT-TYPE
        SYNTAX          DisplayString
        MAX-ACCESS      read-only
        STATUS          current
        DESCRIPTION
            "Station device type"
        ::= { stationAssurEntry 15 }

    staAssurDeviceClass OBJECT-TYPE
        SYNTAX          DisplayString
        MAX-ACCESS      read-only
        STATUS          current
        DESCRIPTION
            "Station device class"
        ::= { stationAssurEntry 16 }

    staAssurActiveAlarmTimestamp OBJECT-TYPE
        SYNTAX          Counter32
        MAX-ACCESS      read-only
        STATUS          current
        DESCRIPTION
            "Last active alarm time (in seconds)"
        ::= { stationAssurEntry 17 }

    staAssurActiveAlarmType OBJECT-TYPE
        SYNTAX          INTEGER { none(0), assoc-time(1), auth-fails(2),
                                  error-rate(3), retry-rate(4), data-rate(5),
                                  rssi(6), snr(7), distance(8) }
        MAX-ACCESS      read-only
        STATUS          current
        DESCRIPTION
            "Last active alarm type"
        ::= { stationAssurEntry 18 }

    staAssurAssocTimeTimestamp OBJECT-TYPE
        SYNTAX          Counter32
        MAX-ACCESS      read-only
        STATUS          current
        DESCRIPTION
            "Last associated time alarm time (in seconds)"
        ::= { stationAssurEntry 19 }

    staAssurAuthFailuresTimestamp OBJECT-TYPE
        SYNTAX          Counter32
        MAX-ACCESS      read-only
        STATUS          current
        DESCRIPTION
            "Last authentication failures alarm time (in seconds)"
        ::= { stationAssurEntry 20 }

    staAssurErrorRateTimestamp OBJECT-TYPE
        SYNTAX          Counter32
        MAX-ACCESS      read-only
        STATUS          current
        DESCRIPTION
            "Last packet error rate alarm time (in seconds)"
        ::= { stationAssurEntry 21 }

    staAssurRetryRateTimestamp OBJECT-TYPE
        SYNTAX          Counter32
        MAX-ACCESS      read-only
        STATUS          current
        DESCRIPTION
            "Last packet retry rate alarm time (in seconds)"
        ::= { stationAssurEntry 22 }

    staAssurDataRateTimestamp OBJECT-TYPE
        SYNTAX          Counter32
        MAX-ACCESS      read-only
        STATUS          current
        DESCRIPTION
            "Last packet data rate alarm time (in seconds)"
        ::= { stationAssurEntry 23 }

    staAssurRSSITimestamp OBJECT-TYPE
        SYNTAX          Counter32
        MAX-ACCESS      read-only
        STATUS          current
        DESCRIPTION
            "Last RSSI alarm time (in seconds)"
        ::= { stationAssurEntry 24 }

    staAssurSNRTimestamp OBJECT-TYPE
        SYNTAX          Counter32
        MAX-ACCESS      read-only
        STATUS          current
        DESCRIPTION
            "Last SNR alarm time (in seconds)"
        ::= { stationAssurEntry 25 }

    staAssurDistanceTimestamp OBJECT-TYPE
        SYNTAX          Counter32
        MAX-ACCESS      read-only
        STATUS          current
        DESCRIPTION
            "Last distance alarm time (in seconds)"
        ::= { stationAssurEntry 26 }

    staAssurAssocTimeActive OBJECT-TYPE
        SYNTAX          INTEGER { inactive(0), active(1) }
        MAX-ACCESS      read-only
        STATUS          current
        DESCRIPTION
            "Flag indicating whether associated time alarm is currently active"
        ::= { stationAssurEntry 27 }

    staAssurAuthFailuresActive OBJECT-TYPE
        SYNTAX          INTEGER { inactive(0), active(1) }
        MAX-ACCESS      read-only
        STATUS          current
        DESCRIPTION
            "Flag indicating whether authentication failures alarm is currently active"
        ::= { stationAssurEntry 28 }

    staAssurErrorRateActive OBJECT-TYPE
        SYNTAX          INTEGER { inactive(0), active(1) }
        MAX-ACCESS      read-only
        STATUS          current
        DESCRIPTION
            "Flag indicating whether error rate alarm is currently active"
        ::= { stationAssurEntry 29 }

    staAssurRetryRateActive OBJECT-TYPE
        SYNTAX          INTEGER { inactive(0), active(1) }
        MAX-ACCESS      read-only
        STATUS          current
        DESCRIPTION
            "Flag indicating whether retry rate alarm is currently active"
        ::= { stationAssurEntry 30 }

    staAssurDataRateActive OBJECT-TYPE
        SYNTAX          INTEGER { inactive(0), active(1) }
        MAX-ACCESS      read-only
        STATUS          current
        DESCRIPTION
            "Flag indicating whether data rate alarm is currently active"
        ::= { stationAssurEntry 31 }

    staAssurRSSIActive OBJECT-TYPE
        SYNTAX          INTEGER { inactive(0), active(1) }
        MAX-ACCESS      read-only
        STATUS          current
        DESCRIPTION
            "Flag indicating whether RSSI alarm is currently active"
        ::= { stationAssurEntry 32 }

    staAssurSNRActive OBJECT-TYPE
        SYNTAX          INTEGER { inactive(0), active(1) }
        MAX-ACCESS      read-only
        STATUS          current
        DESCRIPTION
            "Flag indicating whether SNR alarm is currently active"
        ::= { stationAssurEntry 33 }

    staAssurDistanceActive OBJECT-TYPE
        SYNTAX          INTEGER { inactive(0), active(1) }
        MAX-ACCESS      read-only
        STATUS          current
        DESCRIPTION
            "Flag indicating whether distance alarm is currently active"
        ::= { stationAssurEntry 34 }

    staAssurAlarmType OBJECT-TYPE
        SYNTAX          INTEGER { none(0), assoc-time(1), auth-fails(2),
                                  error-rate(3), retry-rate(4), data-rate(5),
                                  rssi(6), snr(7), distance(8) }
        MAX-ACCESS      read-only
        STATUS          current
        DESCRIPTION
            "Last alarm type"
        ::= { stationAssurEntry 35 }

    stationAssuranceTableClear OBJECT-TYPE
        SYNTAX          INTEGER { history(0), all (1) }
        MAX-ACCESS      read-write
        STATUS          current
        DESCRIPTION
            "Clear station assurance table information"
        ::= { stationAssurance 13 }

    stationAssuranceTablePeriod OBJECT-TYPE
        SYNTAX          Counter32(0..100000000)
        MAX-ACCESS      read-write
        STATUS          current
        DESCRIPTION
            "Specify period for station assurance table entries (in seconds, 0 - all table entries)"
        ::= { stationAssurance 14 }

    stationUnassociatedTablePeriod OBJECT-TYPE
        SYNTAX          Counter32(0..100000000)
        MAX-ACCESS      read-write
        STATUS          current
        DESCRIPTION
            "Specify period for unassociated station table entries (in seconds, 0 - all table entries)"
        ::= { stations 7 }

--
-- STATION LOCATION
--

    stationLocTable OBJECT-TYPE
        SYNTAX          SEQUENCE OF StationLocEntry
        MAX-ACCESS      not-accessible
        STATUS          current
        DESCRIPTION
            "Table of stations and their location (indexed by station MAC address)"
        ::= { stations 8 }

    stationLocEntry OBJECT-TYPE
        SYNTAX          StationLocEntry
        MAX-ACCESS      not-accessible
        STATUS          current
        DESCRIPTION
            "Table entry for station location"
        INDEX       { stationLocMACAddress }
        ::= { stationLocTable 1 }

    StationLocEntry ::= SEQUENCE {
        stationLocMACAddress  DisplayString,
        stationLocRSSI        Integer32,
        stationLocPositionX   DisplayString,
        stationLocPositionY   DisplayString,
        stationLocPositionZ   DisplayString
    }

    stationLocMACAddress OBJECT-TYPE
        SYNTAX          DisplayString
        MAX-ACCESS      read-only
        STATUS          current
        DESCRIPTION
            "MAC address of the station"
        ::= { stationLocEntry 1 }

    stationLocRSSI OBJECT-TYPE
        SYNTAX          Integer32
        MAX-ACCESS      read-only
        STATUS          current
        DESCRIPTION
            "Station's RSSI (last packet received)"
        ::= { stationLocEntry 2 }

    stationLocPositionX OBJECT-TYPE
        SYNTAX          DisplayString
        MAX-ACCESS      read-only
        STATUS          current
        DESCRIPTION
            "Station position X coordinate"
        ::= { stationLocEntry 3 }

    stationLocPositionY OBJECT-TYPE
        SYNTAX          DisplayString
        MAX-ACCESS      read-only
        STATUS          current
        DESCRIPTION
            "Station position Y coordinate"
        ::= { stationLocEntry 4 }

    stationLocPositionZ OBJECT-TYPE
        SYNTAX          DisplayString
        MAX-ACCESS      read-only
        STATUS          current
        DESCRIPTION
            "Station position Z coordinate"
        ::= { stationLocEntry 5 }

--
-- STATISTICS
--

    ethStatsTable OBJECT-TYPE
        SYNTAX          SEQUENCE OF EthStatsEntry
        MAX-ACCESS      not-accessible
        STATUS          current
        DESCRIPTION
            "Table of ethernet statistics"
        ::= { statistics 1 }

    ethStatsEntry OBJECT-TYPE
        SYNTAX          EthStatsEntry
        MAX-ACCESS      not-accessible
        STATUS          current
        DESCRIPTION
            "Table entry for ethernet statistics"
        INDEX       { ethStatsIndex }
        ::= { ethStatsTable 1 }

    EthStatsEntry ::= SEQUENCE {
        ethStatsIndex               Integer32,
        ethStatsIfaceName           DisplayString,
        ethStatsIfaceStatus         INTEGER,
        ethStatsIfaceLink           INTEGER,
        ethStatsIfaceDuplex         INTEGER,
        ethStatsIfaceSpeed          Integer32,
        ethStatsRxBytes             Counter64,
        ethStatsRxPackets           Counter64,
        ethStatsRxCompressed        Counter64,
        ethStatsRxMulticast         Counter64,
        ethStatsRxDropped           Counter64,
        ethStatsRxFifoErrors        Counter64,
        ethStatsRxFrameErrors       Counter64,
        ethStatsRxTotalErrors       Counter64,
        ethStatsTxBytes             Counter64,
        ethStatsTxPackets           Counter64,
        ethStatsTxCompressed        Counter64,
        ethStatsTxCarrierErrors     Counter64,
        ethStatsTxDropped           Counter64,
        ethStatsTxFifoErrors        Counter64,
        ethStatsTxCollisions        Counter64,
        ethStatsTxTotalErrors       Counter64,
        ethStatsTimePeriod          Counter32
    }

    ethStatsIndex OBJECT-TYPE
        SYNTAX          Integer32
        MAX-ACCESS      not-accessible
        STATUS          current
        DESCRIPTION
            "Ethernet statistics index"
        ::= { ethStatsEntry 1 }

    ethStatsIfaceName OBJECT-TYPE
        SYNTAX          DisplayString
        MAX-ACCESS      read-only
        STATUS          current
        DESCRIPTION
            "Interface name"
        ::= { ethStatsEntry 2 }

    ethStatsIfaceStatus OBJECT-TYPE
        SYNTAX          INTEGER { disabled(0), enabled(1) }
        MAX-ACCESS      read-only
        STATUS          current
        DESCRIPTION
            "Interface status"
        ::= { ethStatsEntry 3 }

    ethStatsIfaceLink OBJECT-TYPE
        SYNTAX          INTEGER { down(0), up(1) }
        MAX-ACCESS      read-only
        STATUS          current
        DESCRIPTION
            "Interface link status"
        ::= { ethStatsEntry 4 }

    ethStatsIfaceDuplex OBJECT-TYPE
        SYNTAX          INTEGER { half(0), full(1) }
        MAX-ACCESS      read-only
        STATUS          current
        DESCRIPTION
            "Interface duplex"
        ::= { ethStatsEntry 5 }

    ethStatsIfaceSpeed OBJECT-TYPE
        SYNTAX          Integer32
        MAX-ACCESS      read-only
        STATUS          current
        DESCRIPTION
            "Interface speed"
        ::= { ethStatsEntry 6 }

    ethStatsRxBytes OBJECT-TYPE
        SYNTAX          Counter64
        MAX-ACCESS      read-only
        STATUS          current
        DESCRIPTION
            "Bytes received"
        ::= { ethStatsEntry 7 }

    ethStatsRxPackets OBJECT-TYPE
        SYNTAX          Counter64
        MAX-ACCESS      read-only
        STATUS          current
        DESCRIPTION
            "Packets received"
        ::= { ethStatsEntry 8 }

    ethStatsRxCompressed OBJECT-TYPE
        SYNTAX          Counter64
        MAX-ACCESS      read-only
        STATUS          current
        DESCRIPTION
            "Compressed packets received"
        ::= { ethStatsEntry 9 }

    ethStatsRxMulticast OBJECT-TYPE
        SYNTAX          Counter64
        MAX-ACCESS      read-only
        STATUS          current
        DESCRIPTION
            "Multicast packets received"
        ::= { ethStatsEntry 10 }

    ethStatsRxDropped OBJECT-TYPE
        SYNTAX          Counter64
        MAX-ACCESS      read-only
        STATUS          current
        DESCRIPTION
            "Rx dropped packets"
        ::= { ethStatsEntry 11 }

    ethStatsRxFifoErrors OBJECT-TYPE
        SYNTAX          Counter64
        MAX-ACCESS      read-only
        STATUS          current
        DESCRIPTION
            "Rx fifo errors"
        ::= { ethStatsEntry 12 }

    ethStatsRxFrameErrors OBJECT-TYPE
        SYNTAX          Counter64
        MAX-ACCESS      read-only
        STATUS          current
        DESCRIPTION
            "Rx frame errors"
        ::= { ethStatsEntry 13 }

    ethStatsRxTotalErrors OBJECT-TYPE
        SYNTAX          Counter64
        MAX-ACCESS      read-only
        STATUS          current
        DESCRIPTION
            "Rx total errors"
        ::= { ethStatsEntry 14 }

    ethStatsTxBytes OBJECT-TYPE
        SYNTAX          Counter64
        MAX-ACCESS      read-only
        STATUS          current
        DESCRIPTION
            "Bytes transmitted"
        ::= { ethStatsEntry 15 }

    ethStatsTxPackets OBJECT-TYPE
        SYNTAX          Counter64
        MAX-ACCESS      read-only
        STATUS          current
        DESCRIPTION
            "Packets transmitted"
        ::= { ethStatsEntry 16 }

    ethStatsTxCompressed OBJECT-TYPE
        SYNTAX          Counter64
        MAX-ACCESS      read-only
        STATUS          current
        DESCRIPTION
            "Compressed packets transmitted"
        ::= { ethStatsEntry 17 }

    ethStatsTxCarrierErrors OBJECT-TYPE
        SYNTAX          Counter64
        MAX-ACCESS      read-only
        STATUS          current
        DESCRIPTION
            "Tx carrier errors"
        ::= { ethStatsEntry 18 }

    ethStatsTxDropped OBJECT-TYPE
        SYNTAX          Counter64
        MAX-ACCESS      read-only
        STATUS          current
        DESCRIPTION
            "Tx dropped packets"
        ::= { ethStatsEntry 19 }

    ethStatsTxFifoErrors OBJECT-TYPE
        SYNTAX          Counter64
        MAX-ACCESS      read-only
        STATUS          current
        DESCRIPTION
            "Tx fifo errors"
        ::= { ethStatsEntry 20 }

    ethStatsTxCollisions OBJECT-TYPE
        SYNTAX          Counter64
        MAX-ACCESS      read-only
        STATUS          current
        DESCRIPTION
            "Tx collisions"
        ::= { ethStatsEntry 21 }

    ethStatsTxTotalErrors OBJECT-TYPE
        SYNTAX          Counter64
        MAX-ACCESS      read-only
        STATUS          current
        DESCRIPTION
            "Tx total errors"
        ::= { ethStatsEntry 22 }

    ethStatsTimePeriod OBJECT-TYPE
        SYNTAX          Counter32
        MAX-ACCESS      read-only
        STATUS          current
        DESCRIPTION
            "Time period over which stats were collected"
        ::= { ethStatsEntry 23 }

    iapStatsTable OBJECT-TYPE
        SYNTAX          SEQUENCE OF IapStatsEntry
        MAX-ACCESS      not-accessible
        STATUS          current
        DESCRIPTION
            "Table of IAP statistics"
        ::= { statistics 2 }

    iapStatsEntry OBJECT-TYPE
        SYNTAX          IapStatsEntry
        MAX-ACCESS      not-accessible
        STATUS          current
        DESCRIPTION
            "Table entry for IAP statistics"
        INDEX       { iapStatsIndex }
        ::= { iapStatsTable 1 }

    IapStatsEntry ::= SEQUENCE {
        iapStatsIndex               Integer32,
        iapStatsIfaceName           DisplayString,
        iapStatsRxBytes             Counter64,
        iapStatsRxPackets           Counter64,
        iapStatsRxUnicast           Counter64,
        iapStatsRxMulticast         Counter64,
        iapStatsRxBroadcast         Counter64,
        iapStatsRxManagement        Counter64,
        iapStatsRxBeacons           Counter64,
        iapStatsRxRTS               Counter64,
        iapStatsRxCTS               Counter64,
        iapStatsRxFragments         Counter64,
        iapStatsRxTotalErrors       Counter64,
        iapStatsRxTotalRetries      Counter64,
        iapStatsRxDropped           Counter64,
        iapStatsRxUnassociated      Counter64,
        iapStatsRxCRCErrors         Counter64,
        iapStatsRxFragErrors        Counter64,
        iapStatsRxEncErrors         Counter64,
        iapStatsRxOverruns          Counter64,
        iapStatsRxDuplicates        Counter64,
        iapStatsRxRate1Bytes        Counter64,
        iapStatsRxRate1Packets      Counter64,
        iapStatsRxRate1Errors       Counter64,
        iapStatsRxRate1Retries      Counter64,
        iapStatsRxRate2Bytes        Counter64,
        iapStatsRxRate2Packets      Counter64,
        iapStatsRxRate2Errors       Counter64,
        iapStatsRxRate2Retries      Counter64,
        iapStatsRxRate5Bytes        Counter64,
        iapStatsRxRate5Packets      Counter64,
        iapStatsRxRate5Errors       Counter64,
        iapStatsRxRate5Retries      Counter64,
        iapStatsRxRate11Bytes       Counter64,
        iapStatsRxRate11Packets     Counter64,
        iapStatsRxRate11Errors      Counter64,
        iapStatsRxRate11Retries     Counter64,
        iapStatsRxRate6Bytes        Counter64,
        iapStatsRxRate6Packets      Counter64,
        iapStatsRxRate6Errors       Counter64,
        iapStatsRxRate6Retries      Counter64,
        iapStatsRxRate9Bytes        Counter64,
        iapStatsRxRate9Packets      Counter64,
        iapStatsRxRate9Errors       Counter64,
        iapStatsRxRate9Retries      Counter64,
        iapStatsRxRate12Bytes       Counter64,
        iapStatsRxRate12Packets     Counter64,
        iapStatsRxRate12Errors      Counter64,
        iapStatsRxRate12Retries     Counter64,
        iapStatsRxRate18Bytes       Counter64,
        iapStatsRxRate18Packets     Counter64,
        iapStatsRxRate18Errors      Counter64,
        iapStatsRxRate18Retries     Counter64,
        iapStatsRxRate24Bytes       Counter64,
        iapStatsRxRate24Packets     Counter64,
        iapStatsRxRate24Errors      Counter64,
        iapStatsRxRate24Retries     Counter64,
        iapStatsRxRate36Bytes       Counter64,
        iapStatsRxRate36Packets     Counter64,
        iapStatsRxRate36Errors      Counter64,
        iapStatsRxRate36Retries     Counter64,
        iapStatsRxRate48Bytes       Counter64,
        iapStatsRxRate48Packets     Counter64,
        iapStatsRxRate48Errors      Counter64,
        iapStatsRxRate48Retries     Counter64,
        iapStatsRxRate54Bytes       Counter64,
        iapStatsRxRate54Packets     Counter64,
        iapStatsRxRate54Errors      Counter64,
        iapStatsRxRate54Retries     Counter64,
        iapStatsTxBytes             Counter64,
        iapStatsTxPackets           Counter64,
        iapStatsTxUnicast           Counter64,
        iapStatsTxMulticast         Counter64,
        iapStatsTxBroadcast         Counter64,
        iapStatsTxManagement        Counter64,
        iapStatsTxBeacons           Counter64,
        iapStatsTxRTS               Counter64,
        iapStatsTxCTS               Counter64,
        iapStatsTxFragments         Counter64,
        iapStatsTxTotalErrors       Counter64,
        iapStatsTxTotalRetries      Counter64,
        iapStatsTxDropped           Counter64,
        iapStatsTxUnassociated      Counter64,
        iapStatsTxACKFailures       Counter64,
        iapStatsTxRTSFailures       Counter64,
        iapStatsTxRTSRetries        Counter64,
        iapStatsTxSingleRetries     Counter64,
        iapStatsTxMultipleRetries   Counter64,
        iapStatsTxRate1Bytes        Counter64,
        iapStatsTxRate1Packets      Counter64,
        iapStatsTxRate1Errors       Counter64,
        iapStatsTxRate1Retries      Counter64,
        iapStatsTxRate2Bytes        Counter64,
        iapStatsTxRate2Packets      Counter64,
        iapStatsTxRate2Errors       Counter64,
        iapStatsTxRate2Retries      Counter64,
        iapStatsTxRate5Bytes        Counter64,
        iapStatsTxRate5Packets      Counter64,
        iapStatsTxRate5Errors       Counter64,
        iapStatsTxRate5Retries      Counter64,
        iapStatsTxRate11Bytes       Counter64,
        iapStatsTxRate11Packets     Counter64,
        iapStatsTxRate11Errors      Counter64,
        iapStatsTxRate11Retries     Counter64,
        iapStatsTxRate6Bytes        Counter64,
        iapStatsTxRate6Packets      Counter64,
        iapStatsTxRate6Errors       Counter64,
        iapStatsTxRate6Retries      Counter64,
        iapStatsTxRate9Bytes        Counter64,
        iapStatsTxRate9Packets      Counter64,
        iapStatsTxRate9Errors       Counter64,
        iapStatsTxRate9Retries      Counter64,
        iapStatsTxRate12Bytes       Counter64,
        iapStatsTxRate12Packets     Counter64,
        iapStatsTxRate12Errors      Counter64,
        iapStatsTxRate12Retries     Counter64,
        iapStatsTxRate18Bytes       Counter64,
        iapStatsTxRate18Packets     Counter64,
        iapStatsTxRate18Errors      Counter64,
        iapStatsTxRate18Retries     Counter64,
        iapStatsTxRate24Bytes       Counter64,
        iapStatsTxRate24Packets     Counter64,
        iapStatsTxRate24Errors      Counter64,
        iapStatsTxRate24Retries     Counter64,
        iapStatsTxRate36Bytes       Counter64,
        iapStatsTxRate36Packets     Counter64,
        iapStatsTxRate36Errors      Counter64,
        iapStatsTxRate36Retries     Counter64,
        iapStatsTxRate48Bytes       Counter64,
        iapStatsTxRate48Packets     Counter64,
        iapStatsTxRate48Errors      Counter64,
        iapStatsTxRate48Retries     Counter64,
        iapStatsTxRate54Bytes       Counter64,
        iapStatsTxRate54Packets     Counter64,
        iapStatsTxRate54Errors      Counter64,
        iapStatsTxRate54Retries     Counter64,
        iapStatsTxUtilization       Counter64,
        iapStatsNoiseTotal          Counter64,
        iapStatsNoiseDenominator    Counter64,
        iapStatsTimePeriod          Counter32
    }

    iapStatsIndex OBJECT-TYPE
        SYNTAX          Integer32
        MAX-ACCESS      not-accessible
        STATUS          current
        DESCRIPTION
            "IAP statistics index"
        ::= { iapStatsEntry 1 }

    iapStatsIfaceName OBJECT-TYPE
        SYNTAX          DisplayString
        MAX-ACCESS      read-only
        STATUS          current
        DESCRIPTION
            "Interface name"
        ::= { iapStatsEntry 2 }

    iapStatsRxBytes OBJECT-TYPE
        SYNTAX          Counter64
        MAX-ACCESS      read-only
        STATUS          current
        DESCRIPTION
            "Bytes received"
        ::= { iapStatsEntry 3 }

    iapStatsRxPackets OBJECT-TYPE
        SYNTAX          Counter64
        MAX-ACCESS      read-only
        STATUS          current
        DESCRIPTION
            "Packets received"
        ::= { iapStatsEntry 4 }

    iapStatsRxUnicast OBJECT-TYPE
        SYNTAX          Counter64
        MAX-ACCESS      read-only
        STATUS          current
        DESCRIPTION
            "Unicast packets received"
        ::= { iapStatsEntry 5 }

    iapStatsRxMulticast OBJECT-TYPE
        SYNTAX          Counter64
        MAX-ACCESS      read-only
        STATUS          current
        DESCRIPTION
            "Multicast packets received"
        ::= { iapStatsEntry 6 }

    iapStatsRxBroadcast OBJECT-TYPE
        SYNTAX          Counter64
        MAX-ACCESS      read-only
        STATUS          current
        DESCRIPTION
            "Broadcast packets received"
        ::= { iapStatsEntry 7 }

    iapStatsRxManagement OBJECT-TYPE
        SYNTAX          Counter64
        MAX-ACCESS      read-only
        STATUS          current
        DESCRIPTION
            "Management packets received"
        ::= { iapStatsEntry 8 }

    iapStatsRxBeacons OBJECT-TYPE
        SYNTAX          Counter64
        MAX-ACCESS      read-only
        STATUS          current
        DESCRIPTION
            "Beacons received"
        ::= { iapStatsEntry 9 }

    iapStatsRxRTS OBJECT-TYPE
        SYNTAX          Counter64
        MAX-ACCESS      read-only
        STATUS          current
        DESCRIPTION
            "RTS packets received"
        ::= { iapStatsEntry 10 }

    iapStatsRxCTS OBJECT-TYPE
        SYNTAX          Counter64
        MAX-ACCESS      read-only
        STATUS          current
        DESCRIPTION
            "CTS packets received"
        ::= { iapStatsEntry 11 }

    iapStatsRxFragments OBJECT-TYPE
        SYNTAX          Counter64
        MAX-ACCESS      read-only
        STATUS          current
        DESCRIPTION
            "Fragments received"
        ::= { iapStatsEntry 12 }

    iapStatsRxTotalErrors OBJECT-TYPE
        SYNTAX          Counter64
        MAX-ACCESS      read-only
        STATUS          current
        DESCRIPTION
            "Rx total errors"
        ::= { iapStatsEntry 13 }

    iapStatsRxTotalRetries OBJECT-TYPE
        SYNTAX          Counter64
        MAX-ACCESS      read-only
        STATUS          current
        DESCRIPTION
            "Rx total retries"
        ::= { iapStatsEntry 14 }

    iapStatsRxDropped OBJECT-TYPE
        SYNTAX          Counter64
        MAX-ACCESS      read-only
        STATUS          current
        DESCRIPTION
            "Rx dropped packets"
        ::= { iapStatsEntry 15 }

    iapStatsRxUnassociated OBJECT-TYPE
        SYNTAX          Counter64
        MAX-ACCESS      read-only
        STATUS          current
        DESCRIPTION
            "Rx packets from unassociated stations"
        ::= { iapStatsEntry 16 }

    iapStatsRxCRCErrors OBJECT-TYPE
        SYNTAX          Counter64
        MAX-ACCESS      read-only
        STATUS          current
        DESCRIPTION
            "Rx CRC errors"
        ::= { iapStatsEntry 17 }

    iapStatsRxFragErrors OBJECT-TYPE
        SYNTAX          Counter64
        MAX-ACCESS      read-only
        STATUS          current
        DESCRIPTION
            "Rx fragment errors"
        ::= { iapStatsEntry 18 }

    iapStatsRxEncErrors OBJECT-TYPE
        SYNTAX          Counter64
        MAX-ACCESS      read-only
        STATUS          current
        DESCRIPTION
            "Rx encryption errors"
        ::= { iapStatsEntry 19 }

    iapStatsRxOverruns OBJECT-TYPE
        SYNTAX          Counter64
        MAX-ACCESS      read-only
        STATUS          current
        DESCRIPTION
            "Rx overruns"
        ::= { iapStatsEntry 20 }

    iapStatsRxDuplicates OBJECT-TYPE
        SYNTAX          Counter64
        MAX-ACCESS      read-only
        STATUS          current
        DESCRIPTION
            "Rx duplicates"
        ::= { iapStatsEntry 21 }

    iapStatsRxRate1Bytes OBJECT-TYPE
        SYNTAX          Counter64
        MAX-ACCESS      read-only
        STATUS          current
        DESCRIPTION
            "Bytes received at rate 1Mbps"
        ::= { iapStatsEntry 22 }

    iapStatsRxRate1Packets OBJECT-TYPE
        SYNTAX          Counter64
        MAX-ACCESS      read-only
        STATUS          current
        DESCRIPTION
            "Packets received at rate 1Mbps"
        ::= { iapStatsEntry 23 }

    iapStatsRxRate1Errors OBJECT-TYPE
        SYNTAX          Counter64
        MAX-ACCESS      read-only
        STATUS          current
        DESCRIPTION
            "Rx errors at rate 1Mbps"
        ::= { iapStatsEntry 24 }

    iapStatsRxRate1Retries OBJECT-TYPE
        SYNTAX          Counter64
        MAX-ACCESS      read-only
        STATUS          current
        DESCRIPTION
            "Rx retries at rate 1Mbps"
        ::= { iapStatsEntry 25 }

    iapStatsRxRate2Bytes OBJECT-TYPE
        SYNTAX          Counter64
        MAX-ACCESS      read-only
        STATUS          current
        DESCRIPTION
            "Bytes received at rate 2Mbps"
        ::= { iapStatsEntry 26 }

    iapStatsRxRate2Packets OBJECT-TYPE
        SYNTAX          Counter64
        MAX-ACCESS      read-only
        STATUS          current
        DESCRIPTION
            "Packets received at rate 2Mbps"
        ::= { iapStatsEntry 27 }

    iapStatsRxRate2Errors OBJECT-TYPE
        SYNTAX          Counter64
        MAX-ACCESS      read-only
        STATUS          current
        DESCRIPTION
            "Rx errors at rate 2Mbps"
        ::= { iapStatsEntry 28 }

    iapStatsRxRate2Retries OBJECT-TYPE
        SYNTAX          Counter64
        MAX-ACCESS      read-only
        STATUS          current
        DESCRIPTION
            "Rx retries at rate 2Mbps"
        ::= { iapStatsEntry 29 }

    iapStatsRxRate5Bytes OBJECT-TYPE
        SYNTAX          Counter64
        MAX-ACCESS      read-only
        STATUS          current
        DESCRIPTION
            "Bytes received at rate 5.5Mbps"
        ::= { iapStatsEntry 30 }

    iapStatsRxRate5Packets OBJECT-TYPE
        SYNTAX          Counter64
        MAX-ACCESS      read-only
        STATUS          current
        DESCRIPTION
            "Packets received at rate 5.5Mbps"
        ::= { iapStatsEntry 31 }

    iapStatsRxRate5Errors OBJECT-TYPE
        SYNTAX          Counter64
        MAX-ACCESS      read-only
        STATUS          current
        DESCRIPTION
            "Rx errors at rate 5.5Mbps"
        ::= { iapStatsEntry 32 }

    iapStatsRxRate5Retries OBJECT-TYPE
        SYNTAX          Counter64
        MAX-ACCESS      read-only
        STATUS          current
        DESCRIPTION
            "Rx retries at rate 5.5Mbps"
        ::= { iapStatsEntry 33 }

    iapStatsRxRate11Bytes OBJECT-TYPE
        SYNTAX          Counter64
        MAX-ACCESS      read-only
        STATUS          current
        DESCRIPTION
            "Bytes received at rate 11Mbps"
        ::= { iapStatsEntry 34 }

    iapStatsRxRate11Packets OBJECT-TYPE
        SYNTAX          Counter64
        MAX-ACCESS      read-only
        STATUS          current
        DESCRIPTION
            "Packets received at rate 11Mbps"
        ::= { iapStatsEntry 35 }

    iapStatsRxRate11Errors OBJECT-TYPE
        SYNTAX          Counter64
        MAX-ACCESS      read-only
        STATUS          current
        DESCRIPTION
            "Rx errors at rate 11Mbps"
        ::= { iapStatsEntry 36 }

    iapStatsRxRate11Retries OBJECT-TYPE
        SYNTAX          Counter64
        MAX-ACCESS      read-only
        STATUS          current
        DESCRIPTION
            "Rx retries at rate 11Mbps"
        ::= { iapStatsEntry 37 }

    iapStatsRxRate6Bytes OBJECT-TYPE
        SYNTAX          Counter64
        MAX-ACCESS      read-only
        STATUS          current
        DESCRIPTION
            "Bytes received at rate 6Mbps"
        ::= { iapStatsEntry 38 }

    iapStatsRxRate6Packets OBJECT-TYPE
        SYNTAX          Counter64
        MAX-ACCESS      read-only
        STATUS          current
        DESCRIPTION
            "Packets received at rate 6Mbps"
        ::= { iapStatsEntry 39 }

    iapStatsRxRate6Errors OBJECT-TYPE
        SYNTAX          Counter64
        MAX-ACCESS      read-only
        STATUS          current
        DESCRIPTION
            "Rx errors at rate 6Mbps"
        ::= { iapStatsEntry 40 }

    iapStatsRxRate6Retries OBJECT-TYPE
        SYNTAX          Counter64
        MAX-ACCESS      read-only
        STATUS          current
        DESCRIPTION
            "Rx retries at rate 6Mbps"
        ::= { iapStatsEntry 41 }

    iapStatsRxRate9Bytes OBJECT-TYPE
        SYNTAX          Counter64
        MAX-ACCESS      read-only
        STATUS          current
        DESCRIPTION
            "Bytes received at rate 9Mbps"
        ::= { iapStatsEntry 42 }

    iapStatsRxRate9Packets OBJECT-TYPE
        SYNTAX          Counter64
        MAX-ACCESS      read-only
        STATUS          current
        DESCRIPTION
            "Packets received at rate 9Mbps"
        ::= { iapStatsEntry 43 }

    iapStatsRxRate9Errors OBJECT-TYPE
        SYNTAX          Counter64
        MAX-ACCESS      read-only
        STATUS          current
        DESCRIPTION
            "Rx errors at rate 9Mbps"
        ::= { iapStatsEntry 44 }

    iapStatsRxRate9Retries OBJECT-TYPE
        SYNTAX          Counter64
        MAX-ACCESS      read-only
        STATUS          current
        DESCRIPTION
            "Rx retries at rate 9Mbps"
        ::= { iapStatsEntry 45 }

    iapStatsRxRate12Bytes OBJECT-TYPE
        SYNTAX          Counter64
        MAX-ACCESS      read-only
        STATUS          current
        DESCRIPTION
            "Bytes received at rate 12Mbps"
        ::= { iapStatsEntry 46 }

    iapStatsRxRate12Packets OBJECT-TYPE
        SYNTAX          Counter64
        MAX-ACCESS      read-only
        STATUS          current
        DESCRIPTION
            "Packets received at rate 12Mbps"
        ::= { iapStatsEntry 47 }

    iapStatsRxRate12Errors OBJECT-TYPE
        SYNTAX          Counter64
        MAX-ACCESS      read-only
        STATUS          current
        DESCRIPTION
            "Rx errors at rate 12Mbps"
        ::= { iapStatsEntry 48 }

    iapStatsRxRate12Retries OBJECT-TYPE
        SYNTAX          Counter64
        MAX-ACCESS      read-only
        STATUS          current
        DESCRIPTION
            "Rx retries at rate 12Mbps"
        ::= { iapStatsEntry 49 }

    iapStatsRxRate18Bytes OBJECT-TYPE
        SYNTAX          Counter64
        MAX-ACCESS      read-only
        STATUS          current
        DESCRIPTION
            "Bytes received at rate 18Mbps"
        ::= { iapStatsEntry 50 }

    iapStatsRxRate18Packets OBJECT-TYPE
        SYNTAX          Counter64
        MAX-ACCESS      read-only
        STATUS          current
        DESCRIPTION
            "Packets received at rate 18Mbps"
        ::= { iapStatsEntry 51 }

    iapStatsRxRate18Errors OBJECT-TYPE
        SYNTAX          Counter64
        MAX-ACCESS      read-only
        STATUS          current
        DESCRIPTION
            "Rx errors at rate 18Mbps"
        ::= { iapStatsEntry 52 }

    iapStatsRxRate18Retries OBJECT-TYPE
        SYNTAX          Counter64
        MAX-ACCESS      read-only
        STATUS          current
        DESCRIPTION
            "Rx retries at rate 18Mbps"
        ::= { iapStatsEntry 53 }

    iapStatsRxRate24Bytes OBJECT-TYPE
        SYNTAX          Counter64
        MAX-ACCESS      read-only
        STATUS          current
        DESCRIPTION
            "Bytes received at rate 24Mbps"
        ::= { iapStatsEntry 54 }

    iapStatsRxRate24Packets OBJECT-TYPE
        SYNTAX          Counter64
        MAX-ACCESS      read-only
        STATUS          current
        DESCRIPTION
            "Packets received at rate 24Mbps"
        ::= { iapStatsEntry 55 }

    iapStatsRxRate24Errors OBJECT-TYPE
        SYNTAX          Counter64
        MAX-ACCESS      read-only
        STATUS          current
        DESCRIPTION
            "Rx errors at rate 24Mbps"
        ::= { iapStatsEntry 56 }

    iapStatsRxRate24Retries OBJECT-TYPE
        SYNTAX          Counter64
        MAX-ACCESS      read-only
        STATUS          current
        DESCRIPTION
            "Rx retries at rate 24Mbps"
        ::= { iapStatsEntry 57 }

    iapStatsRxRate36Bytes OBJECT-TYPE
        SYNTAX          Counter64
        MAX-ACCESS      read-only
        STATUS          current
        DESCRIPTION
            "Bytes received at rate 36Mbps"
        ::= { iapStatsEntry 58 }

    iapStatsRxRate36Packets OBJECT-TYPE
        SYNTAX          Counter64
        MAX-ACCESS      read-only
        STATUS          current
        DESCRIPTION
            "Packets received at rate 36Mbps"
        ::= { iapStatsEntry 59 }

    iapStatsRxRate36Errors OBJECT-TYPE
        SYNTAX          Counter64
        MAX-ACCESS      read-only
        STATUS          current
        DESCRIPTION
            "Rx errors at rate 36Mbps"
        ::= { iapStatsEntry 60 }

    iapStatsRxRate36Retries OBJECT-TYPE
        SYNTAX          Counter64
        MAX-ACCESS      read-only
        STATUS          current
        DESCRIPTION
            "Rx retries at rate 36Mbps"
        ::= { iapStatsEntry 61 }

    iapStatsRxRate48Bytes OBJECT-TYPE
        SYNTAX          Counter64
        MAX-ACCESS      read-only
        STATUS          current
        DESCRIPTION
            "Bytes received at rate 48Mbps"
        ::= { iapStatsEntry 62 }

    iapStatsRxRate48Packets OBJECT-TYPE
        SYNTAX          Counter64
        MAX-ACCESS      read-only
        STATUS          current
        DESCRIPTION
            "Packets received at rate 48Mbps"
        ::= { iapStatsEntry 63 }

    iapStatsRxRate48Errors OBJECT-TYPE
        SYNTAX          Counter64
        MAX-ACCESS      read-only
        STATUS          current
        DESCRIPTION
            "Rx errors at rate 48Mbps"
        ::= { iapStatsEntry 64 }

    iapStatsRxRate48Retries OBJECT-TYPE
        SYNTAX          Counter64
        MAX-ACCESS      read-only
        STATUS          current
        DESCRIPTION
            "Rx retries at rate 48Mbps"
        ::= { iapStatsEntry 65 }

    iapStatsRxRate54Bytes OBJECT-TYPE
        SYNTAX          Counter64
        MAX-ACCESS      read-only
        STATUS          current
        DESCRIPTION
            "Bytes received at rate 54Mbps"
        ::= { iapStatsEntry 66 }

    iapStatsRxRate54Packets OBJECT-TYPE
        SYNTAX          Counter64
        MAX-ACCESS      read-only
        STATUS          current
        DESCRIPTION
            "Packets received at rate 54Mbps"
        ::= { iapStatsEntry 67 }

    iapStatsRxRate54Errors OBJECT-TYPE
        SYNTAX          Counter64
        MAX-ACCESS      read-only
        STATUS          current
        DESCRIPTION
            "Rx errors at rate 54Mbps"
        ::= { iapStatsEntry 68 }

    iapStatsRxRate54Retries OBJECT-TYPE
        SYNTAX          Counter64
        MAX-ACCESS      read-only
        STATUS          current
        DESCRIPTION
            "Rx retries at rate 54Mbps"
        ::= { iapStatsEntry 69 }

    iapStatsTxBytes OBJECT-TYPE
        SYNTAX          Counter64
        MAX-ACCESS      read-only
        STATUS          current
        DESCRIPTION
            "Bytes transmitted"
        ::= { iapStatsEntry 70 }

    iapStatsTxPackets OBJECT-TYPE
        SYNTAX          Counter64
        MAX-ACCESS      read-only
        STATUS          current
        DESCRIPTION
            "Packets transmitted"
        ::= { iapStatsEntry 71 }

    iapStatsTxUnicast OBJECT-TYPE
        SYNTAX          Counter64
        MAX-ACCESS      read-only
        STATUS          current
        DESCRIPTION
            "Unicast packets transmitted"
        ::= { iapStatsEntry 72 }

    iapStatsTxMulticast OBJECT-TYPE
        SYNTAX          Counter64
        MAX-ACCESS      read-only
        STATUS          current
        DESCRIPTION
            "Multicast packets transmitted"
        ::= { iapStatsEntry 73 }

    iapStatsTxBroadcast OBJECT-TYPE
        SYNTAX          Counter64
        MAX-ACCESS      read-only
        STATUS          current
        DESCRIPTION
            "Broadcast packets transmitted"
        ::= { iapStatsEntry 74 }

    iapStatsTxManagement OBJECT-TYPE
        SYNTAX          Counter64
        MAX-ACCESS      read-only
        STATUS          current
        DESCRIPTION
            "Management packets transmitted"
        ::= { iapStatsEntry 75 }

    iapStatsTxBeacons OBJECT-TYPE
        SYNTAX          Counter64
        MAX-ACCESS      read-only
        STATUS          current
        DESCRIPTION
            "Beacons transmitted"
        ::= { iapStatsEntry 76 }

    iapStatsTxRTS OBJECT-TYPE
        SYNTAX          Counter64
        MAX-ACCESS      read-only
        STATUS          current
        DESCRIPTION
            "RTS packets transmitted"
        ::= { iapStatsEntry 77 }

    iapStatsTxCTS OBJECT-TYPE
        SYNTAX          Counter64
        MAX-ACCESS      read-only
        STATUS          current
        DESCRIPTION
            "CTS packets transmitted"
        ::= { iapStatsEntry 78 }

    iapStatsTxFragments OBJECT-TYPE
        SYNTAX          Counter64
        MAX-ACCESS      read-only
        STATUS          current
        DESCRIPTION
            "Fragments transmitted"
        ::= { iapStatsEntry 79 }

    iapStatsTxTotalErrors OBJECT-TYPE
        SYNTAX          Counter64
        MAX-ACCESS      read-only
        STATUS          current
        DESCRIPTION
            "Tx total errors"
        ::= { iapStatsEntry 80 }

    iapStatsTxTotalRetries OBJECT-TYPE
        SYNTAX          Counter64
        MAX-ACCESS      read-only
        STATUS          current
        DESCRIPTION
            "Tx total retries"
        ::= { iapStatsEntry 81 }

    iapStatsTxDropped OBJECT-TYPE
        SYNTAX          Counter64
        MAX-ACCESS      read-only
        STATUS          current
        DESCRIPTION
            "Tx dropped packets"
        ::= { iapStatsEntry 82 }

    iapStatsTxUnassociated OBJECT-TYPE
        SYNTAX          Counter64
        MAX-ACCESS      read-only
        STATUS          current
        DESCRIPTION
            "Tx packets to unassociated stations"
        ::= { iapStatsEntry 83 }

    iapStatsTxACKFailures OBJECT-TYPE
        SYNTAX          Counter64
        MAX-ACCESS      read-only
        STATUS          current
        DESCRIPTION
            "Tx ACK failures"
        ::= { iapStatsEntry 84 }

    iapStatsTxRTSFailures OBJECT-TYPE
        SYNTAX          Counter64
        MAX-ACCESS      read-only
        STATUS          current
        DESCRIPTION
            "Tx RTS failures"
        ::= { iapStatsEntry 85 }

    iapStatsTxRTSRetries OBJECT-TYPE
        SYNTAX          Counter64
        MAX-ACCESS      read-only
        STATUS          current
        DESCRIPTION
            "Tx RTS retries"
        ::= { iapStatsEntry 86 }

    iapStatsTxSingleRetries OBJECT-TYPE
        SYNTAX          Counter64
        MAX-ACCESS      read-only
        STATUS          current
        DESCRIPTION
            "Tx single retries"
        ::= { iapStatsEntry 87 }

    iapStatsTxMultipleRetries OBJECT-TYPE
        SYNTAX          Counter64
        MAX-ACCESS      read-only
        STATUS          current
        DESCRIPTION
            "Tx multiple retries"
        ::= { iapStatsEntry 88 }

    iapStatsTxRate1Bytes OBJECT-TYPE
        SYNTAX          Counter64
        MAX-ACCESS      read-only
        STATUS          current
        DESCRIPTION
            "Bytes transmitted at rate 1Mbps"
        ::= { iapStatsEntry 89 }

    iapStatsTxRate1Packets OBJECT-TYPE
        SYNTAX          Counter64
        MAX-ACCESS      read-only
        STATUS          current
        DESCRIPTION
            "Packets transmitted at rate 1Mbps"
        ::= { iapStatsEntry 90 }

    iapStatsTxRate1Errors OBJECT-TYPE
        SYNTAX          Counter64
        MAX-ACCESS      read-only
        STATUS          current
        DESCRIPTION
            "Tx errors at rate 1Mbps"
        ::= { iapStatsEntry 91 }

    iapStatsTxRate1Retries OBJECT-TYPE
        SYNTAX          Counter64
        MAX-ACCESS      read-only
        STATUS          current
        DESCRIPTION
            "Tx retries at rate 1Mbps"
        ::= { iapStatsEntry 92 }

    iapStatsTxRate2Bytes OBJECT-TYPE
        SYNTAX          Counter64
        MAX-ACCESS      read-only
        STATUS          current
        DESCRIPTION
            "Bytes transmitted at rate 2Mbps"
        ::= { iapStatsEntry 93 }

    iapStatsTxRate2Packets OBJECT-TYPE
        SYNTAX          Counter64
        MAX-ACCESS      read-only
        STATUS          current
        DESCRIPTION
            "Packets transmitted at rate 2Mbps"
        ::= { iapStatsEntry 94 }

    iapStatsTxRate2Errors OBJECT-TYPE
        SYNTAX          Counter64
        MAX-ACCESS      read-only
        STATUS          current
        DESCRIPTION
            "Tx errors at rate 2Mbps"
        ::= { iapStatsEntry 95 }

    iapStatsTxRate2Retries OBJECT-TYPE
        SYNTAX          Counter64
        MAX-ACCESS      read-only
        STATUS          current
        DESCRIPTION
            "Tx retries at rate 2Mbps"
        ::= { iapStatsEntry 96 }

    iapStatsTxRate5Bytes OBJECT-TYPE
        SYNTAX          Counter64
        MAX-ACCESS      read-only
        STATUS          current
        DESCRIPTION
            "Bytes transmitted at rate 5.5Mbps"
        ::= { iapStatsEntry 97 }

    iapStatsTxRate5Packets OBJECT-TYPE
        SYNTAX          Counter64
        MAX-ACCESS      read-only
        STATUS          current
        DESCRIPTION
            "Packets transmitted at rate 5.5Mbps"
        ::= { iapStatsEntry 98 }

    iapStatsTxRate5Errors OBJECT-TYPE
        SYNTAX          Counter64
        MAX-ACCESS      read-only
        STATUS          current
        DESCRIPTION
            "Tx errors at rate 5.5Mbps"
        ::= { iapStatsEntry 99 }

    iapStatsTxRate5Retries OBJECT-TYPE
        SYNTAX          Counter64
        MAX-ACCESS      read-only
        STATUS          current
        DESCRIPTION
            "Tx retries at rate 5.5Mbps"
        ::= { iapStatsEntry 100 }

    iapStatsTxRate11Bytes OBJECT-TYPE
        SYNTAX          Counter64
        MAX-ACCESS      read-only
        STATUS          current
        DESCRIPTION
            "Bytes transmitted at rate 11Mbps"
        ::= { iapStatsEntry 101 }

    iapStatsTxRate11Packets OBJECT-TYPE
        SYNTAX          Counter64
        MAX-ACCESS      read-only
        STATUS          current
        DESCRIPTION
            "Packets transmitted at rate 11Mbps"
        ::= { iapStatsEntry 102 }

    iapStatsTxRate11Errors OBJECT-TYPE
        SYNTAX          Counter64
        MAX-ACCESS      read-only
        STATUS          current
        DESCRIPTION
            "Tx errors at rate 11Mbps"
        ::= { iapStatsEntry 103 }

    iapStatsTxRate11Retries OBJECT-TYPE
        SYNTAX          Counter64
        MAX-ACCESS      read-only
        STATUS          current
        DESCRIPTION
            "Tx retries at rate 11Mbps"
        ::= { iapStatsEntry 104 }

    iapStatsTxRate6Bytes OBJECT-TYPE
        SYNTAX          Counter64
        MAX-ACCESS      read-only
        STATUS          current
        DESCRIPTION
            "Bytes transmitted at rate 6Mbps"
        ::= { iapStatsEntry 105 }

    iapStatsTxRate6Packets OBJECT-TYPE
        SYNTAX          Counter64
        MAX-ACCESS      read-only
        STATUS          current
        DESCRIPTION
            "Packets transmitted at rate 6Mbps"
        ::= { iapStatsEntry 106 }

    iapStatsTxRate6Errors OBJECT-TYPE
        SYNTAX          Counter64
        MAX-ACCESS      read-only
        STATUS          current
        DESCRIPTION
            "Tx errors at rate 6Mbps"
        ::= { iapStatsEntry 107 }

    iapStatsTxRate6Retries OBJECT-TYPE
        SYNTAX          Counter64
        MAX-ACCESS      read-only
        STATUS          current
        DESCRIPTION
            "Tx retries at rate 6Mbps"
        ::= { iapStatsEntry 108 }

    iapStatsTxRate9Bytes OBJECT-TYPE
        SYNTAX          Counter64
        MAX-ACCESS      read-only
        STATUS          current
        DESCRIPTION
            "Bytes transmitted at rate 9Mbps"
        ::= { iapStatsEntry 109 }

    iapStatsTxRate9Packets OBJECT-TYPE
        SYNTAX          Counter64
        MAX-ACCESS      read-only
        STATUS          current
        DESCRIPTION
            "Packets transmitted at rate 9Mbps"
        ::= { iapStatsEntry 110 }

    iapStatsTxRate9Errors OBJECT-TYPE
        SYNTAX          Counter64
        MAX-ACCESS      read-only
        STATUS          current
        DESCRIPTION
            "Tx errors at rate 9Mbps"
        ::= { iapStatsEntry 111 }

    iapStatsTxRate9Retries OBJECT-TYPE
        SYNTAX          Counter64
        MAX-ACCESS      read-only
        STATUS          current
        DESCRIPTION
            "Tx retries at rate 9Mbps"
        ::= { iapStatsEntry 112 }

    iapStatsTxRate12Bytes OBJECT-TYPE
        SYNTAX          Counter64
        MAX-ACCESS      read-only
        STATUS          current
        DESCRIPTION
            "Bytes transmitted at rate 12Mbps"
        ::= { iapStatsEntry 113 }

    iapStatsTxRate12Packets OBJECT-TYPE
        SYNTAX          Counter64
        MAX-ACCESS      read-only
        STATUS          current
        DESCRIPTION
            "Packets transmitted at rate 12Mbps"
        ::= { iapStatsEntry 114 }

    iapStatsTxRate12Errors OBJECT-TYPE
        SYNTAX          Counter64
        MAX-ACCESS      read-only
        STATUS          current
        DESCRIPTION
            "Tx errors at rate 12Mbps"
        ::= { iapStatsEntry 115 }

    iapStatsTxRate12Retries OBJECT-TYPE
        SYNTAX          Counter64
        MAX-ACCESS      read-only
        STATUS          current
        DESCRIPTION
            "Tx retries at rate 12Mbps"
        ::= { iapStatsEntry 116 }

    iapStatsTxRate18Bytes OBJECT-TYPE
        SYNTAX          Counter64
        MAX-ACCESS      read-only
        STATUS          current
        DESCRIPTION
            "Bytes transmitted at rate 18Mbps"
        ::= { iapStatsEntry 117 }

    iapStatsTxRate18Packets OBJECT-TYPE
        SYNTAX          Counter64
        MAX-ACCESS      read-only
        STATUS          current
        DESCRIPTION
            "Packets transmitted at rate 18Mbps"
        ::= { iapStatsEntry 118 }

    iapStatsTxRate18Errors OBJECT-TYPE
        SYNTAX          Counter64
        MAX-ACCESS      read-only
        STATUS          current
        DESCRIPTION
            "Tx errors at rate 18Mbps"
        ::= { iapStatsEntry 119 }

    iapStatsTxRate18Retries OBJECT-TYPE
        SYNTAX          Counter64
        MAX-ACCESS      read-only
        STATUS          current
        DESCRIPTION
            "Tx retries at rate 18Mbps"
        ::= { iapStatsEntry 120 }

    iapStatsTxRate24Bytes OBJECT-TYPE
        SYNTAX          Counter64
        MAX-ACCESS      read-only
        STATUS          current
        DESCRIPTION
            "Bytes transmitted at rate 24Mbps"
        ::= { iapStatsEntry 121 }

    iapStatsTxRate24Packets OBJECT-TYPE
        SYNTAX          Counter64
        MAX-ACCESS      read-only
        STATUS          current
        DESCRIPTION
            "Packets transmitted at rate 24Mbps"
        ::= { iapStatsEntry 122 }

    iapStatsTxRate24Errors OBJECT-TYPE
        SYNTAX          Counter64
        MAX-ACCESS      read-only
        STATUS          current
        DESCRIPTION
            "Tx errors at rate 24Mbps"
        ::= { iapStatsEntry 123 }

    iapStatsTxRate24Retries OBJECT-TYPE
        SYNTAX          Counter64
        MAX-ACCESS      read-only
        STATUS          current
        DESCRIPTION
            "Tx retries at rate 24Mbps"
        ::= { iapStatsEntry 124 }

    iapStatsTxRate36Bytes OBJECT-TYPE
        SYNTAX          Counter64
        MAX-ACCESS      read-only
        STATUS          current
        DESCRIPTION
            "Bytes transmitted at rate 36Mbps"
        ::= { iapStatsEntry 125 }

    iapStatsTxRate36Packets OBJECT-TYPE
        SYNTAX          Counter64
        MAX-ACCESS      read-only
        STATUS          current
        DESCRIPTION
            "Packets transmitted at rate 36Mbps"
        ::= { iapStatsEntry 126 }

    iapStatsTxRate36Errors OBJECT-TYPE
        SYNTAX          Counter64
        MAX-ACCESS      read-only
        STATUS          current
        DESCRIPTION
            "Tx errors at rate 36Mbps"
        ::= { iapStatsEntry 127 }

    iapStatsTxRate36Retries OBJECT-TYPE
        SYNTAX          Counter64
        MAX-ACCESS      read-only
        STATUS          current
        DESCRIPTION
            "Tx retries at rate 36Mbps"
        ::= { iapStatsEntry 128 }

    iapStatsTxRate48Bytes OBJECT-TYPE
        SYNTAX          Counter64
        MAX-ACCESS      read-only
        STATUS          current
        DESCRIPTION
            "Bytes transmitted at rate 48Mbps"
        ::= { iapStatsEntry 129 }

    iapStatsTxRate48Packets OBJECT-TYPE
        SYNTAX          Counter64
        MAX-ACCESS      read-only
        STATUS          current
        DESCRIPTION
            "Packets transmitted at rate 48Mbps"
        ::= { iapStatsEntry 130 }

    iapStatsTxRate48Errors OBJECT-TYPE
        SYNTAX          Counter64
        MAX-ACCESS      read-only
        STATUS          current
        DESCRIPTION
            "Tx errors at rate 48Mbps"
        ::= { iapStatsEntry 131 }

    iapStatsTxRate48Retries OBJECT-TYPE
        SYNTAX          Counter64
        MAX-ACCESS      read-only
        STATUS          current
        DESCRIPTION
            "Tx retries at rate 48Mbps"
        ::= { iapStatsEntry 132 }

    iapStatsTxRate54Bytes OBJECT-TYPE
        SYNTAX          Counter64
        MAX-ACCESS      read-only
        STATUS          current
        DESCRIPTION
            "Bytes transmitted at rate 54Mbps"
        ::= { iapStatsEntry 133 }

    iapStatsTxRate54Packets OBJECT-TYPE
        SYNTAX          Counter64
        MAX-ACCESS      read-only
        STATUS          current
        DESCRIPTION
            "Packets transmitted at rate 54Mbps"
        ::= { iapStatsEntry 134 }

    iapStatsTxRate54Errors OBJECT-TYPE
        SYNTAX          Counter64
        MAX-ACCESS      read-only
        STATUS          current
        DESCRIPTION
            "Tx errors at rate 54Mbps"
        ::= { iapStatsEntry 135 }

    iapStatsTxRate54Retries OBJECT-TYPE
        SYNTAX          Counter64
        MAX-ACCESS      read-only
        STATUS          current
        DESCRIPTION
            "Tx retries at rate 54Mbps"
        ::= { iapStatsEntry 136 }

    iapStatsTxUtilization OBJECT-TYPE
        SYNTAX          Counter64
        MAX-ACCESS      read-only
        STATUS          current
        DESCRIPTION
            "Total mS during which IAP has been transmitting"
        ::= { iapStatsEntry 137 }

    iapStatsNoiseTotal OBJECT-TYPE
        SYNTAX          Counter64
        MAX-ACCESS      read-only
        STATUS          current
        DESCRIPTION
            "Total silence*bytes for all packets received by IAP"
        ::= { iapStatsEntry 138 }

    iapStatsNoiseDenominator OBJECT-TYPE
        SYNTAX          Counter64
        MAX-ACCESS      read-only
        STATUS          current
        DESCRIPTION
            "Total bytes in all packets received by IAP"
        ::= { iapStatsEntry 139 }

    iapStatsTimePeriod OBJECT-TYPE
        SYNTAX          Counter32
        MAX-ACCESS      read-only
        STATUS          current
        DESCRIPTION
            "Time period over which stats were collected"
        ::= { iapStatsEntry 140 }

    stationStatsTable OBJECT-TYPE
        SYNTAX          SEQUENCE OF StationStatsEntry
        MAX-ACCESS      not-accessible
        STATUS          current
        DESCRIPTION
            "Table of station statistics"
        ::= { statistics 3 }

    stationStatsEntry OBJECT-TYPE
        SYNTAX          StationStatsEntry
        MAX-ACCESS      not-accessible
        STATUS          current
        DESCRIPTION
            "Table entry for station statistics"
        INDEX       { stationStatsIndex }
        ::= { stationStatsTable 1 }

    StationStatsEntry ::= SEQUENCE {
        stationStatsIndex               Integer32,
        stationStatsMACAddress          DisplayString,
        stationStatsRxBytes             Counter64,
        stationStatsRxPackets           Counter64,
        stationStatsRxErrors            Counter64,
        stationStatsRxRetries           Counter64,
        stationStatsRxRate1Bytes        Counter64,
        stationStatsRxRate1Packets      Counter64,
        stationStatsRxRate1Errors       Counter64,
        stationStatsRxRate1Retries      Counter64,
        stationStatsRxRate2Bytes        Counter64,
        stationStatsRxRate2Packets      Counter64,
        stationStatsRxRate2Errors       Counter64,
        stationStatsRxRate2Retries      Counter64,
        stationStatsRxRate5Bytes        Counter64,
        stationStatsRxRate5Packets      Counter64,
        stationStatsRxRate5Errors       Counter64,
        stationStatsRxRate5Retries      Counter64,
        stationStatsRxRate11Bytes       Counter64,
        stationStatsRxRate11Packets     Counter64,
        stationStatsRxRate11Errors      Counter64,
        stationStatsRxRate11Retries     Counter64,
        stationStatsRxRate6Bytes        Counter64,
        stationStatsRxRate6Packets      Counter64,
        stationStatsRxRate6Errors       Counter64,
        stationStatsRxRate6Retries      Counter64,
        stationStatsRxRate9Bytes        Counter64,
        stationStatsRxRate9Packets      Counter64,
        stationStatsRxRate9Errors       Counter64,
        stationStatsRxRate9Retries      Counter64,
        stationStatsRxRate12Bytes       Counter64,
        stationStatsRxRate12Packets     Counter64,
        stationStatsRxRate12Errors      Counter64,
        stationStatsRxRate12Retries     Counter64,
        stationStatsRxRate18Bytes       Counter64,
        stationStatsRxRate18Packets     Counter64,
        stationStatsRxRate18Errors      Counter64,
        stationStatsRxRate18Retries     Counter64,
        stationStatsRxRate24Bytes       Counter64,
        stationStatsRxRate24Packets     Counter64,
        stationStatsRxRate24Errors      Counter64,
        stationStatsRxRate24Retries     Counter64,
        stationStatsRxRate36Bytes       Counter64,
        stationStatsRxRate36Packets     Counter64,
        stationStatsRxRate36Errors      Counter64,
        stationStatsRxRate36Retries     Counter64,
        stationStatsRxRate48Bytes       Counter64,
        stationStatsRxRate48Packets     Counter64,
        stationStatsRxRate48Errors      Counter64,
        stationStatsRxRate48Retries     Counter64,
        stationStatsRxRate54Bytes       Counter64,
        stationStatsRxRate54Packets     Counter64,
        stationStatsRxRate54Errors      Counter64,
        stationStatsRxRate54Retries     Counter64,
        stationStatsTxBytes             Counter64,
        stationStatsTxPackets           Counter64,
        stationStatsTxErrors            Counter64,
        stationStatsTxRetries           Counter64,
        stationStatsTxRate1Bytes        Counter64,
        stationStatsTxRate1Packets      Counter64,
        stationStatsTxRate1Errors       Counter64,
        stationStatsTxRate1Retries      Counter64,
        stationStatsTxRate2Bytes        Counter64,
        stationStatsTxRate2Packets      Counter64,
        stationStatsTxRate2Errors       Counter64,
        stationStatsTxRate2Retries      Counter64,
        stationStatsTxRate5Bytes        Counter64,
        stationStatsTxRate5Packets      Counter64,
        stationStatsTxRate5Errors       Counter64,
        stationStatsTxRate5Retries      Counter64,
        stationStatsTxRate11Bytes       Counter64,
        stationStatsTxRate11Packets     Counter64,
        stationStatsTxRate11Errors      Counter64,
        stationStatsTxRate11Retries     Counter64,
        stationStatsTxRate6Bytes        Counter64,
        stationStatsTxRate6Packets      Counter64,
        stationStatsTxRate6Errors       Counter64,
        stationStatsTxRate6Retries      Counter64,
        stationStatsTxRate9Bytes        Counter64,
        stationStatsTxRate9Packets      Counter64,
        stationStatsTxRate9Errors       Counter64,
        stationStatsTxRate9Retries      Counter64,
        stationStatsTxRate12Bytes       Counter64,
        stationStatsTxRate12Packets     Counter64,
        stationStatsTxRate12Errors      Counter64,
        stationStatsTxRate12Retries     Counter64,
        stationStatsTxRate18Bytes       Counter64,
        stationStatsTxRate18Packets     Counter64,
        stationStatsTxRate18Errors      Counter64,
        stationStatsTxRate18Retries     Counter64,
        stationStatsTxRate24Bytes       Counter64,
        stationStatsTxRate24Packets     Counter64,
        stationStatsTxRate24Errors      Counter64,
        stationStatsTxRate24Retries     Counter64,
        stationStatsTxRate36Bytes       Counter64,
        stationStatsTxRate36Packets     Counter64,
        stationStatsTxRate36Errors      Counter64,
        stationStatsTxRate36Retries     Counter64,
        stationStatsTxRate48Bytes       Counter64,
        stationStatsTxRate48Packets     Counter64,
        stationStatsTxRate48Errors      Counter64,
        stationStatsTxRate48Retries     Counter64,
        stationStatsTxRate54Bytes       Counter64,
        stationStatsTxRate54Packets     Counter64,
        stationStatsTxRate54Errors      Counter64,
        stationStatsTxRate54Retries     Counter64,
        stationStatsTimePeriod          Counter32
    }

    stationStatsIndex OBJECT-TYPE
        SYNTAX          Integer32
        MAX-ACCESS      not-accessible
        STATUS          current
        DESCRIPTION
            "Station statistics index"
        ::= { stationStatsEntry 1 }

    stationStatsMACAddress OBJECT-TYPE
        SYNTAX          DisplayString
        MAX-ACCESS      read-only
        STATUS          current
        DESCRIPTION
            "MAC address of the station"
        ::= { stationStatsEntry 2 }

    stationStatsRxBytes OBJECT-TYPE
        SYNTAX          Counter64
        MAX-ACCESS      read-only
        STATUS          current
        DESCRIPTION
            "Bytes received"
        ::= { stationStatsEntry 3 }

    stationStatsRxPackets OBJECT-TYPE
        SYNTAX          Counter64
        MAX-ACCESS      read-only
        STATUS          current
        DESCRIPTION
            "Packets received"
        ::= { stationStatsEntry 4 }

    stationStatsRxErrors OBJECT-TYPE
        SYNTAX          Counter64
        MAX-ACCESS      read-only
        STATUS          current
        DESCRIPTION
            "Rx errors"
        ::= { stationStatsEntry 5 }

    stationStatsRxRetries OBJECT-TYPE
        SYNTAX          Counter64
        MAX-ACCESS      read-only
        STATUS          current
        DESCRIPTION
            "Rx retries"
        ::= { stationStatsEntry 6 }

    stationStatsRxRate1Bytes OBJECT-TYPE
        SYNTAX          Counter64
        MAX-ACCESS      read-only
        STATUS          current
        DESCRIPTION
            "Bytes received at rate 1Mbps"
        ::= { stationStatsEntry 7 }

    stationStatsRxRate1Packets OBJECT-TYPE
        SYNTAX          Counter64
        MAX-ACCESS      read-only
        STATUS          current
        DESCRIPTION
            "Packets received at rate 1Mbps"
        ::= { stationStatsEntry 8 }

    stationStatsRxRate1Errors OBJECT-TYPE
        SYNTAX          Counter64
        MAX-ACCESS      read-only
        STATUS          current
        DESCRIPTION
            "Rx errors at rate 1Mbps"
        ::= { stationStatsEntry 9 }

    stationStatsRxRate1Retries OBJECT-TYPE
        SYNTAX          Counter64
        MAX-ACCESS      read-only
        STATUS          current
        DESCRIPTION
            "Rx retries at rate 1Mbps"
        ::= { stationStatsEntry 10 }

    stationStatsRxRate2Bytes OBJECT-TYPE
        SYNTAX          Counter64
        MAX-ACCESS      read-only
        STATUS          current
        DESCRIPTION
            "Bytes received at rate 2Mbps"
        ::= { stationStatsEntry 11 }

    stationStatsRxRate2Packets OBJECT-TYPE
        SYNTAX          Counter64
        MAX-ACCESS      read-only
        STATUS          current
        DESCRIPTION
            "Packets received at rate 2Mbps"
        ::= { stationStatsEntry 12 }

    stationStatsRxRate2Errors OBJECT-TYPE
        SYNTAX          Counter64
        MAX-ACCESS      read-only
        STATUS          current
        DESCRIPTION
            "Rx errors at rate 2Mbps"
        ::= { stationStatsEntry 13 }

    stationStatsRxRate2Retries OBJECT-TYPE
        SYNTAX          Counter64
        MAX-ACCESS      read-only
        STATUS          current
        DESCRIPTION
            "Rx retries at rate 2Mbps"
        ::= { stationStatsEntry 14 }

    stationStatsRxRate5Bytes OBJECT-TYPE
        SYNTAX          Counter64
        MAX-ACCESS      read-only
        STATUS          current
        DESCRIPTION
            "Bytes received at rate 5.5Mbps"
        ::= { stationStatsEntry 15 }

    stationStatsRxRate5Packets OBJECT-TYPE
        SYNTAX          Counter64
        MAX-ACCESS      read-only
        STATUS          current
        DESCRIPTION
            "Packets received at rate 5.5Mbps"
        ::= { stationStatsEntry 16 }

    stationStatsRxRate5Errors OBJECT-TYPE
        SYNTAX          Counter64
        MAX-ACCESS      read-only
        STATUS          current
        DESCRIPTION
            "Rx errors at rate 5.5Mbps"
        ::= { stationStatsEntry 17 }

    stationStatsRxRate5Retries OBJECT-TYPE
        SYNTAX          Counter64
        MAX-ACCESS      read-only
        STATUS          current
        DESCRIPTION
            "Rx retries at rate 5.5Mbps"
        ::= { stationStatsEntry 18 }

    stationStatsRxRate11Bytes OBJECT-TYPE
        SYNTAX          Counter64
        MAX-ACCESS      read-only
        STATUS          current
        DESCRIPTION
            "Bytes received at rate 11Mbps"
        ::= { stationStatsEntry 19 }

    stationStatsRxRate11Packets OBJECT-TYPE
        SYNTAX          Counter64
        MAX-ACCESS      read-only
        STATUS          current
        DESCRIPTION
            "Packets received at rate 11Mbps"
        ::= { stationStatsEntry 20 }

    stationStatsRxRate11Errors OBJECT-TYPE
        SYNTAX          Counter64
        MAX-ACCESS      read-only
        STATUS          current
        DESCRIPTION
            "Rx errors at rate 11Mbps"
        ::= { stationStatsEntry 21 }

    stationStatsRxRate11Retries OBJECT-TYPE
        SYNTAX          Counter64
        MAX-ACCESS      read-only
        STATUS          current
        DESCRIPTION
            "Rx retries at rate 11Mbps"
        ::= { stationStatsEntry 22 }

    stationStatsRxRate6Bytes OBJECT-TYPE
        SYNTAX          Counter64
        MAX-ACCESS      read-only
        STATUS          current
        DESCRIPTION
            "Bytes received at rate 6Mbps"
        ::= { stationStatsEntry 23 }

    stationStatsRxRate6Packets OBJECT-TYPE
        SYNTAX          Counter64
        MAX-ACCESS      read-only
        STATUS          current
        DESCRIPTION
            "Packets received at rate 6Mbps"
        ::= { stationStatsEntry 24 }

    stationStatsRxRate6Errors OBJECT-TYPE
        SYNTAX          Counter64
        MAX-ACCESS      read-only
        STATUS          current
        DESCRIPTION
            "Rx errors at rate 6Mbps"
        ::= { stationStatsEntry 25 }

    stationStatsRxRate6Retries OBJECT-TYPE
        SYNTAX          Counter64
        MAX-ACCESS      read-only
        STATUS          current
        DESCRIPTION
            "Rx retries at rate 6Mbps"
        ::= { stationStatsEntry 26 }

    stationStatsRxRate9Bytes OBJECT-TYPE
        SYNTAX          Counter64
        MAX-ACCESS      read-only
        STATUS          current
        DESCRIPTION
            "Bytes received at rate 9Mbps"
        ::= { stationStatsEntry 27 }

    stationStatsRxRate9Packets OBJECT-TYPE
        SYNTAX          Counter64
        MAX-ACCESS      read-only
        STATUS          current
        DESCRIPTION
            "Packets received at rate 9Mbps"
        ::= { stationStatsEntry 28 }

    stationStatsRxRate9Errors OBJECT-TYPE
        SYNTAX          Counter64
        MAX-ACCESS      read-only
        STATUS          current
        DESCRIPTION
            "Rx errors at rate 9Mbps"
        ::= { stationStatsEntry 29 }

    stationStatsRxRate9Retries OBJECT-TYPE
        SYNTAX          Counter64
        MAX-ACCESS      read-only
        STATUS          current
        DESCRIPTION
            "Rx retries at rate 9Mbps"
        ::= { stationStatsEntry 30 }

    stationStatsRxRate12Bytes OBJECT-TYPE
        SYNTAX          Counter64
        MAX-ACCESS      read-only
        STATUS          current
        DESCRIPTION
            "Bytes received at rate 12Mbps"
        ::= { stationStatsEntry 31 }

    stationStatsRxRate12Packets OBJECT-TYPE
        SYNTAX          Counter64
        MAX-ACCESS      read-only
        STATUS          current
        DESCRIPTION
            "Packets received at rate 12Mbps"
        ::= { stationStatsEntry 32 }

    stationStatsRxRate12Errors OBJECT-TYPE
        SYNTAX          Counter64
        MAX-ACCESS      read-only
        STATUS          current
        DESCRIPTION
            "Rx errors at rate 12Mbps"
        ::= { stationStatsEntry 33 }

    stationStatsRxRate12Retries OBJECT-TYPE
        SYNTAX          Counter64
        MAX-ACCESS      read-only
        STATUS          current
        DESCRIPTION
            "Rx retries at rate 12Mbps"
        ::= { stationStatsEntry 34 }

    stationStatsRxRate18Bytes OBJECT-TYPE
        SYNTAX          Counter64
        MAX-ACCESS      read-only
        STATUS          current
        DESCRIPTION
            "Bytes received at rate 18Mbps"
        ::= { stationStatsEntry 35 }

    stationStatsRxRate18Packets OBJECT-TYPE
        SYNTAX          Counter64
        MAX-ACCESS      read-only
        STATUS          current
        DESCRIPTION
            "Packets received at rate 18Mbps"
        ::= { stationStatsEntry 36 }

    stationStatsRxRate18Errors OBJECT-TYPE
        SYNTAX          Counter64
        MAX-ACCESS      read-only
        STATUS          current
        DESCRIPTION
            "Rx errors at rate 18Mbps"
        ::= { stationStatsEntry 37 }

    stationStatsRxRate18Retries OBJECT-TYPE
        SYNTAX          Counter64
        MAX-ACCESS      read-only
        STATUS          current
        DESCRIPTION
            "Rx retries at rate 18Mbps"
        ::= { stationStatsEntry 38 }

    stationStatsRxRate24Bytes OBJECT-TYPE
        SYNTAX          Counter64
        MAX-ACCESS      read-only
        STATUS          current
        DESCRIPTION
            "Bytes received at rate 24Mbps"
        ::= { stationStatsEntry 39 }

    stationStatsRxRate24Packets OBJECT-TYPE
        SYNTAX          Counter64
        MAX-ACCESS      read-only
        STATUS          current
        DESCRIPTION
            "Packets received at rate 24Mbps"
        ::= { stationStatsEntry 40 }

    stationStatsRxRate24Errors OBJECT-TYPE
        SYNTAX          Counter64
        MAX-ACCESS      read-only
        STATUS          current
        DESCRIPTION
            "Rx errors at rate 24Mbps"
        ::= { stationStatsEntry 41 }

    stationStatsRxRate24Retries OBJECT-TYPE
        SYNTAX          Counter64
        MAX-ACCESS      read-only
        STATUS          current
        DESCRIPTION
            "Rx retries at rate 24Mbps"
        ::= { stationStatsEntry 42 }

    stationStatsRxRate36Bytes OBJECT-TYPE
        SYNTAX          Counter64
        MAX-ACCESS      read-only
        STATUS          current
        DESCRIPTION
            "Bytes received at rate 36Mbps"
        ::= { stationStatsEntry 43 }

    stationStatsRxRate36Packets OBJECT-TYPE
        SYNTAX          Counter64
        MAX-ACCESS      read-only
        STATUS          current
        DESCRIPTION
            "Packets received at rate 36Mbps"
        ::= { stationStatsEntry 44 }

    stationStatsRxRate36Errors OBJECT-TYPE
        SYNTAX          Counter64
        MAX-ACCESS      read-only
        STATUS          current
        DESCRIPTION
            "Rx errors at rate 36Mbps"
        ::= { stationStatsEntry 45 }

    stationStatsRxRate36Retries OBJECT-TYPE
        SYNTAX          Counter64
        MAX-ACCESS      read-only
        STATUS          current
        DESCRIPTION
            "Rx retries at rate 36Mbps"
        ::= { stationStatsEntry 46 }

    stationStatsRxRate48Bytes OBJECT-TYPE
        SYNTAX          Counter64
        MAX-ACCESS      read-only
        STATUS          current
        DESCRIPTION
            "Bytes received at rate 48Mbps"
        ::= { stationStatsEntry 47 }

    stationStatsRxRate48Packets OBJECT-TYPE
        SYNTAX          Counter64
        MAX-ACCESS      read-only
        STATUS          current
        DESCRIPTION
            "Packets received at rate 48Mbps"
        ::= { stationStatsEntry 48 }

    stationStatsRxRate48Errors OBJECT-TYPE
        SYNTAX          Counter64
        MAX-ACCESS      read-only
        STATUS          current
        DESCRIPTION
            "Rx errors at rate 48Mbps"
        ::= { stationStatsEntry 49 }

    stationStatsRxRate48Retries OBJECT-TYPE
        SYNTAX          Counter64
        MAX-ACCESS      read-only
        STATUS          current
        DESCRIPTION
            "Rx retries at rate 48Mbps"
        ::= { stationStatsEntry 50 }

    stationStatsRxRate54Bytes OBJECT-TYPE
        SYNTAX          Counter64
        MAX-ACCESS      read-only
        STATUS          current
        DESCRIPTION
            "Bytes received at rate 54Mbps"
        ::= { stationStatsEntry 51 }

    stationStatsRxRate54Packets OBJECT-TYPE
        SYNTAX          Counter64
        MAX-ACCESS      read-only
        STATUS          current
        DESCRIPTION
            "Packets received at rate 54Mbps"
        ::= { stationStatsEntry 52 }

    stationStatsRxRate54Errors OBJECT-TYPE
        SYNTAX          Counter64
        MAX-ACCESS      read-only
        STATUS          current
        DESCRIPTION
            "Rx errors at rate 54Mbps"
        ::= { stationStatsEntry 53 }

    stationStatsRxRate54Retries OBJECT-TYPE
        SYNTAX          Counter64
        MAX-ACCESS      read-only
        STATUS          current
        DESCRIPTION
            "Rx retries at rate 54Mbps"
        ::= { stationStatsEntry 54 }

    stationStatsTxBytes OBJECT-TYPE
        SYNTAX          Counter64
        MAX-ACCESS      read-only
        STATUS          current
        DESCRIPTION
            "Bytes transmitted"
        ::= { stationStatsEntry 55 }

    stationStatsTxPackets OBJECT-TYPE
        SYNTAX          Counter64
        MAX-ACCESS      read-only
        STATUS          current
        DESCRIPTION
            "Packets transmitted"
        ::= { stationStatsEntry 56 }

    stationStatsTxErrors OBJECT-TYPE
        SYNTAX          Counter64
        MAX-ACCESS      read-only
        STATUS          current
        DESCRIPTION
            "Tx errors"
        ::= { stationStatsEntry 57 }

    stationStatsTxRetries OBJECT-TYPE
        SYNTAX          Counter64
        MAX-ACCESS      read-only
        STATUS          current
        DESCRIPTION
            "Tx retries"
        ::= { stationStatsEntry 58 }

    stationStatsTxRate1Bytes OBJECT-TYPE
        SYNTAX          Counter64
        MAX-ACCESS      read-only
        STATUS          current
        DESCRIPTION
            "Bytes transmitted at rate 1Mbps"
        ::= { stationStatsEntry 59 }

    stationStatsTxRate1Packets OBJECT-TYPE
        SYNTAX          Counter64
        MAX-ACCESS      read-only
        STATUS          current
        DESCRIPTION
            "Packets transmitted at rate 1Mbps"
        ::= { stationStatsEntry 60 }

    stationStatsTxRate1Errors OBJECT-TYPE
        SYNTAX          Counter64
        MAX-ACCESS      read-only
        STATUS          current
        DESCRIPTION
            "Tx errors at rate 1Mbps"
        ::= { stationStatsEntry 61 }

    stationStatsTxRate1Retries OBJECT-TYPE
        SYNTAX          Counter64
        MAX-ACCESS      read-only
        STATUS          current
        DESCRIPTION
            "Tx retries at rate 1Mbps"
        ::= { stationStatsEntry 62 }

    stationStatsTxRate2Bytes OBJECT-TYPE
        SYNTAX          Counter64
        MAX-ACCESS      read-only
        STATUS          current
        DESCRIPTION
            "Bytes transmitted at rate 2Mbps"
        ::= { stationStatsEntry 63 }

    stationStatsTxRate2Packets OBJECT-TYPE
        SYNTAX          Counter64
        MAX-ACCESS      read-only
        STATUS          current
        DESCRIPTION
            "Packets transmitted at rate 2Mbps"
        ::= { stationStatsEntry 64 }

    stationStatsTxRate2Errors OBJECT-TYPE
        SYNTAX          Counter64
        MAX-ACCESS      read-only
        STATUS          current
        DESCRIPTION
            "Tx errors at rate 2Mbps"
        ::= { stationStatsEntry 65 }

    stationStatsTxRate2Retries OBJECT-TYPE
        SYNTAX          Counter64
        MAX-ACCESS      read-only
        STATUS          current
        DESCRIPTION
            "Tx retries at rate 2Mbps"
        ::= { stationStatsEntry 66 }

    stationStatsTxRate5Bytes OBJECT-TYPE
        SYNTAX          Counter64
        MAX-ACCESS      read-only
        STATUS          current
        DESCRIPTION
            "Bytes transmitted at rate 5.5Mbps"
        ::= { stationStatsEntry 67 }

    stationStatsTxRate5Packets OBJECT-TYPE
        SYNTAX          Counter64
        MAX-ACCESS      read-only
        STATUS          current
        DESCRIPTION
            "Packets transmitted at rate 5.5Mbps"
        ::= { stationStatsEntry 68 }

    stationStatsTxRate5Errors OBJECT-TYPE
        SYNTAX          Counter64
        MAX-ACCESS      read-only
        STATUS          current
        DESCRIPTION
            "Tx errors at rate 5.5Mbps"
        ::= { stationStatsEntry 69 }

    stationStatsTxRate5Retries OBJECT-TYPE
        SYNTAX          Counter64
        MAX-ACCESS      read-only
        STATUS          current
        DESCRIPTION
            "Tx retries at rate 5.5Mbps"
        ::= { stationStatsEntry 70 }

    stationStatsTxRate11Bytes OBJECT-TYPE
        SYNTAX          Counter64
        MAX-ACCESS      read-only
        STATUS          current
        DESCRIPTION
            "Bytes transmitted at rate 11Mbps"
        ::= { stationStatsEntry 71 }

    stationStatsTxRate11Packets OBJECT-TYPE
        SYNTAX          Counter64
        MAX-ACCESS      read-only
        STATUS          current
        DESCRIPTION
            "Packets transmitted at rate 11Mbps"
        ::= { stationStatsEntry 72 }

    stationStatsTxRate11Errors OBJECT-TYPE
        SYNTAX          Counter64
        MAX-ACCESS      read-only
        STATUS          current
        DESCRIPTION
            "Tx errors at rate 11Mbps"
        ::= { stationStatsEntry 73 }

    stationStatsTxRate11Retries OBJECT-TYPE
        SYNTAX          Counter64
        MAX-ACCESS      read-only
        STATUS          current
        DESCRIPTION
            "Tx retries at rate 11Mbps"
        ::= { stationStatsEntry 74 }

    stationStatsTxRate6Bytes OBJECT-TYPE
        SYNTAX          Counter64
        MAX-ACCESS      read-only
        STATUS          current
        DESCRIPTION
            "Bytes transmitted at rate 6Mbps"
        ::= { stationStatsEntry 75 }

    stationStatsTxRate6Packets OBJECT-TYPE
        SYNTAX          Counter64
        MAX-ACCESS      read-only
        STATUS          current
        DESCRIPTION
            "Packets transmitted at rate 6Mbps"
        ::= { stationStatsEntry 76 }

    stationStatsTxRate6Errors OBJECT-TYPE
        SYNTAX          Counter64
        MAX-ACCESS      read-only
        STATUS          current
        DESCRIPTION
            "Tx errors at rate 6Mbps"
        ::= { stationStatsEntry 77 }

    stationStatsTxRate6Retries OBJECT-TYPE
        SYNTAX          Counter64
        MAX-ACCESS      read-only
        STATUS          current
        DESCRIPTION
            "Tx retries at rate 6Mbps"
        ::= { stationStatsEntry 78 }

    stationStatsTxRate9Bytes OBJECT-TYPE
        SYNTAX          Counter64
        MAX-ACCESS      read-only
        STATUS          current
        DESCRIPTION
            "Bytes transmitted at rate 9Mbps"
        ::= { stationStatsEntry 79 }

    stationStatsTxRate9Packets OBJECT-TYPE
        SYNTAX          Counter64
        MAX-ACCESS      read-only
        STATUS          current
        DESCRIPTION
            "Packets transmitted at rate 9Mbps"
        ::= { stationStatsEntry 80 }

    stationStatsTxRate9Errors OBJECT-TYPE
        SYNTAX          Counter64
        MAX-ACCESS      read-only
        STATUS          current
        DESCRIPTION
            "Tx errors at rate 9Mbps"
        ::= { stationStatsEntry 81 }

    stationStatsTxRate9Retries OBJECT-TYPE
        SYNTAX          Counter64
        MAX-ACCESS      read-only
        STATUS          current
        DESCRIPTION
            "Tx retries at rate 9Mbps"
        ::= { stationStatsEntry 82 }

    stationStatsTxRate12Bytes OBJECT-TYPE
        SYNTAX          Counter64
        MAX-ACCESS      read-only
        STATUS          current
        DESCRIPTION
            "Bytes transmitted at rate 12Mbps"
        ::= { stationStatsEntry 83 }

    stationStatsTxRate12Packets OBJECT-TYPE
        SYNTAX          Counter64
        MAX-ACCESS      read-only
        STATUS          current
        DESCRIPTION
            "Packets transmitted at rate 12Mbps"
        ::= { stationStatsEntry 84 }

    stationStatsTxRate12Errors OBJECT-TYPE
        SYNTAX          Counter64
        MAX-ACCESS      read-only
        STATUS          current
        DESCRIPTION
            "Tx errors at rate 12Mbps"
        ::= { stationStatsEntry 85 }

    stationStatsTxRate12Retries OBJECT-TYPE
        SYNTAX          Counter64
        MAX-ACCESS      read-only
        STATUS          current
        DESCRIPTION
            "Tx retries at rate 12Mbps"
        ::= { stationStatsEntry 86 }

    stationStatsTxRate18Bytes OBJECT-TYPE
        SYNTAX          Counter64
        MAX-ACCESS      read-only
        STATUS          current
        DESCRIPTION
            "Bytes transmitted at rate 18Mbps"
        ::= { stationStatsEntry 87 }

    stationStatsTxRate18Packets OBJECT-TYPE
        SYNTAX          Counter64
        MAX-ACCESS      read-only
        STATUS          current
        DESCRIPTION
            "Packets transmitted at rate 18Mbps"
        ::= { stationStatsEntry 88 }

    stationStatsTxRate18Errors OBJECT-TYPE
        SYNTAX          Counter64
        MAX-ACCESS      read-only
        STATUS          current
        DESCRIPTION
            "Tx errors at rate 18Mbps"
        ::= { stationStatsEntry 89 }

    stationStatsTxRate18Retries OBJECT-TYPE
        SYNTAX          Counter64
        MAX-ACCESS      read-only
        STATUS          current
        DESCRIPTION
            "Tx retries at rate 18Mbps"
        ::= { stationStatsEntry 90 }

    stationStatsTxRate24Bytes OBJECT-TYPE
        SYNTAX          Counter64
        MAX-ACCESS      read-only
        STATUS          current
        DESCRIPTION
            "Bytes transmitted at rate 24Mbps"
        ::= { stationStatsEntry 91 }

    stationStatsTxRate24Packets OBJECT-TYPE
        SYNTAX          Counter64
        MAX-ACCESS      read-only
        STATUS          current
        DESCRIPTION
            "Packets transmitted at rate 24Mbps"
        ::= { stationStatsEntry 92 }

    stationStatsTxRate24Errors OBJECT-TYPE
        SYNTAX          Counter64
        MAX-ACCESS      read-only
        STATUS          current
        DESCRIPTION
            "Tx errors at rate 24Mbps"
        ::= { stationStatsEntry 93 }

    stationStatsTxRate24Retries OBJECT-TYPE
        SYNTAX          Counter64
        MAX-ACCESS      read-only
        STATUS          current
        DESCRIPTION
            "Tx retries at rate 24Mbps"
        ::= { stationStatsEntry 94 }

    stationStatsTxRate36Bytes OBJECT-TYPE
        SYNTAX          Counter64
        MAX-ACCESS      read-only
        STATUS          current
        DESCRIPTION
            "Bytes transmitted at rate 36Mbps"
        ::= { stationStatsEntry 95 }

    stationStatsTxRate36Packets OBJECT-TYPE
        SYNTAX          Counter64
        MAX-ACCESS      read-only
        STATUS          current
        DESCRIPTION
            "Packets transmitted at rate 36Mbps"
        ::= { stationStatsEntry 96 }

    stationStatsTxRate36Errors OBJECT-TYPE
        SYNTAX          Counter64
        MAX-ACCESS      read-only
        STATUS          current
        DESCRIPTION
            "Tx errors at rate 36Mbps"
        ::= { stationStatsEntry 97 }

    stationStatsTxRate36Retries OBJECT-TYPE
        SYNTAX          Counter64
        MAX-ACCESS      read-only
        STATUS          current
        DESCRIPTION
            "Tx retries at rate 36Mbps"
        ::= { stationStatsEntry 98 }

    stationStatsTxRate48Bytes OBJECT-TYPE
        SYNTAX          Counter64
        MAX-ACCESS      read-only
        STATUS          current
        DESCRIPTION
            "Bytes transmitted at rate 48Mbps"
        ::= { stationStatsEntry 99 }

    stationStatsTxRate48Packets OBJECT-TYPE
        SYNTAX          Counter64
        MAX-ACCESS      read-only
        STATUS          current
        DESCRIPTION
            "Packets transmitted at rate 48Mbps"
        ::= { stationStatsEntry 100 }

    stationStatsTxRate48Errors OBJECT-TYPE
        SYNTAX          Counter64
        MAX-ACCESS      read-only
        STATUS          current
        DESCRIPTION
            "Tx errors at rate 48Mbps"
        ::= { stationStatsEntry 101 }

    stationStatsTxRate48Retries OBJECT-TYPE
        SYNTAX          Counter64
        MAX-ACCESS      read-only
        STATUS          current
        DESCRIPTION
            "Tx retries at rate 48Mbps"
        ::= { stationStatsEntry 102 }

    stationStatsTxRate54Bytes OBJECT-TYPE
        SYNTAX          Counter64
        MAX-ACCESS      read-only
        STATUS          current
        DESCRIPTION
            "Bytes transmitted at rate 54Mbps"
        ::= { stationStatsEntry 103 }

    stationStatsTxRate54Packets OBJECT-TYPE
        SYNTAX          Counter64
        MAX-ACCESS      read-only
        STATUS          current
        DESCRIPTION
            "Packets transmitted at rate 54Mbps"
        ::= { stationStatsEntry 104 }

    stationStatsTxRate54Errors OBJECT-TYPE
        SYNTAX          Counter64
        MAX-ACCESS      read-only
        STATUS          current
        DESCRIPTION
            "Tx errors at rate 54Mbps"
        ::= { stationStatsEntry 105 }

    stationStatsTxRate54Retries OBJECT-TYPE
        SYNTAX          Counter64
        MAX-ACCESS      read-only
        STATUS          current
        DESCRIPTION
            "Tx retries at rate 54Mbps"
        ::= { stationStatsEntry 106 }

    stationStatsTimePeriod OBJECT-TYPE
        SYNTAX          Counter32
        MAX-ACCESS      read-only
        STATUS          current
        DESCRIPTION
            "Time period over which stats were collected"
        ::= { stationStatsEntry 107 }

    vlanStatsTable OBJECT-TYPE
        SYNTAX          SEQUENCE OF VlanStatsEntry
        MAX-ACCESS      not-accessible
        STATUS          current
        DESCRIPTION
            "Table of VLAN statistics"
        ::= { statistics 4 }

    vlanStatsEntry OBJECT-TYPE
        SYNTAX          VlanStatsEntry
        MAX-ACCESS      not-accessible
        STATUS          current
        DESCRIPTION
            "Table entry for VLAN statistics"
        INDEX       { vlanStatsIndex }
        ::= { vlanStatsTable 1 }

    VlanStatsEntry ::= SEQUENCE {
        vlanStatsIndex              Integer32,
        vlanStatsName               DisplayString,
        vlanStatsNumber             Integer32,
        vlanStatsRxBytes            Counter64,
        vlanStatsRxPackets          Counter64,
        vlanStatsRxCompressed       Counter64,
        vlanStatsRxMulticast        Counter64,
        vlanStatsRxDropped          Counter64,
        vlanStatsRxFifoErrors       Counter64,
        vlanStatsRxFrameErrors      Counter64,
        vlanStatsRxTotalErrors      Counter64,
        vlanStatsTxBytes            Counter64,
        vlanStatsTxPackets          Counter64,
        vlanStatsTxCompressed       Counter64,
        vlanStatsTxCarrierErrors    Counter64,
        vlanStatsTxDropped          Counter64,
        vlanStatsTxFifoErrors       Counter64,
        vlanStatsTxCollisions       Counter64,
        vlanStatsTxTotalErrors      Counter64,
        vlanStatsTimePeriod         Counter32
    }

    vlanStatsIndex OBJECT-TYPE
        SYNTAX          Integer32
        MAX-ACCESS      not-accessible
        STATUS          current
        DESCRIPTION
            "VLAN statistics index"
        ::= { vlanStatsEntry 1 }

    vlanStatsName OBJECT-TYPE
        SYNTAX          DisplayString
        MAX-ACCESS      read-only
        STATUS          current
        DESCRIPTION
            "VLAN name"
        ::= { vlanStatsEntry 2 }

    vlanStatsNumber OBJECT-TYPE
        SYNTAX          Integer32
        MAX-ACCESS      read-only
        STATUS          current
        DESCRIPTION
            "VLAN number"
        ::= { vlanStatsEntry 3 }

    vlanStatsRxBytes OBJECT-TYPE
        SYNTAX          Counter64
        MAX-ACCESS      read-only
        STATUS          current
        DESCRIPTION
            "Bytes received"
        ::= { vlanStatsEntry 4 }

    vlanStatsRxPackets OBJECT-TYPE
        SYNTAX          Counter64
        MAX-ACCESS      read-only
        STATUS          current
        DESCRIPTION
            "Packets received"
        ::= { vlanStatsEntry 5 }

    vlanStatsRxCompressed OBJECT-TYPE
        SYNTAX          Counter64
        MAX-ACCESS      read-only
        STATUS          current
        DESCRIPTION
            "Compressed packets received"
        ::= { vlanStatsEntry 6 }

    vlanStatsRxMulticast OBJECT-TYPE
        SYNTAX          Counter64
        MAX-ACCESS      read-only
        STATUS          current
        DESCRIPTION
            "Multicast packets received"
        ::= { vlanStatsEntry 7 }

    vlanStatsRxDropped OBJECT-TYPE
        SYNTAX          Counter64
        MAX-ACCESS      read-only
        STATUS          current
        DESCRIPTION
            "Rx dropped packets"
        ::= { vlanStatsEntry 8 }

    vlanStatsRxFifoErrors OBJECT-TYPE
        SYNTAX          Counter64
        MAX-ACCESS      read-only
        STATUS          current
        DESCRIPTION
            "Rx fifo errors"
        ::= { vlanStatsEntry 9 }

    vlanStatsRxFrameErrors OBJECT-TYPE
        SYNTAX          Counter64
        MAX-ACCESS      read-only
        STATUS          current
        DESCRIPTION
            "Rx frame errors"
        ::= { vlanStatsEntry 10 }

    vlanStatsRxTotalErrors OBJECT-TYPE
        SYNTAX          Counter64
        MAX-ACCESS      read-only
        STATUS          current
        DESCRIPTION
            "Rx total errors"
        ::= { vlanStatsEntry 11 }

    vlanStatsTxBytes OBJECT-TYPE
        SYNTAX          Counter64
        MAX-ACCESS      read-only
        STATUS          current
        DESCRIPTION
            "Bytes transmitted"
        ::= { vlanStatsEntry 12 }

    vlanStatsTxPackets OBJECT-TYPE
        SYNTAX          Counter64
        MAX-ACCESS      read-only
        STATUS          current
        DESCRIPTION
            "Packets transmitted"
        ::= { vlanStatsEntry 13 }

    vlanStatsTxCompressed OBJECT-TYPE
        SYNTAX          Counter64
        MAX-ACCESS      read-only
        STATUS          current
        DESCRIPTION
            "Compressed packets transmitted"
        ::= { vlanStatsEntry 14 }

    vlanStatsTxCarrierErrors OBJECT-TYPE
        SYNTAX          Counter64
        MAX-ACCESS      read-only
        STATUS          current
        DESCRIPTION
            "Tx carrier errors"
        ::= { vlanStatsEntry 15 }

    vlanStatsTxDropped OBJECT-TYPE
        SYNTAX          Counter64
        MAX-ACCESS      read-only
        STATUS          current
        DESCRIPTION
            "Tx dropped packets"
        ::= { vlanStatsEntry 16 }

    vlanStatsTxFifoErrors OBJECT-TYPE
        SYNTAX          Counter64
        MAX-ACCESS      read-only
        STATUS          current
        DESCRIPTION
            "Tx fifo errors"
        ::= { vlanStatsEntry 17 }

    vlanStatsTxCollisions OBJECT-TYPE
        SYNTAX          Counter64
        MAX-ACCESS      read-only
        STATUS          current
        DESCRIPTION
            "Tx collisions"
        ::= { vlanStatsEntry 18 }

    vlanStatsTxTotalErrors OBJECT-TYPE
        SYNTAX          Counter64
        MAX-ACCESS      read-only
        STATUS          current
        DESCRIPTION
            "Tx total errors"
        ::= { vlanStatsEntry 19 }

    vlanStatsTimePeriod OBJECT-TYPE
        SYNTAX          Counter32
        MAX-ACCESS      read-only
        STATUS          current
        DESCRIPTION
            "Time period over which stats were collected"
        ::= { vlanStatsEntry 20 }

    wdsStatsTable OBJECT-TYPE
        SYNTAX          SEQUENCE OF WdsStatsEntry
        MAX-ACCESS      not-accessible
        STATUS          current
        DESCRIPTION
            "Table of statistics for WDS links"
        ::= { statistics 5 }

    wdsStatsEntry OBJECT-TYPE
        SYNTAX          WdsStatsEntry
        MAX-ACCESS      not-accessible
        STATUS          current
        DESCRIPTION
            "Table entry for WDS link statistics"
        INDEX       { wdsStatsIndex }
        ::= { wdsStatsTable 1 }

    WdsStatsEntry ::= SEQUENCE {
        wdsStatsIndex               Integer32,
        wdsStatsLinkName            DisplayString,
        wdsStatsRxBytes             Counter64,
        wdsStatsRxPackets           Counter64,
        wdsStatsRxErrors            Counter64,
        wdsStatsRxRetries           Counter64,
        wdsStatsRxRate1Bytes        Counter64,
        wdsStatsRxRate1Packets      Counter64,
        wdsStatsRxRate1Errors       Counter64,
        wdsStatsRxRate1Retries      Counter64,
        wdsStatsRxRate2Bytes        Counter64,
        wdsStatsRxRate2Packets      Counter64,
        wdsStatsRxRate2Errors       Counter64,
        wdsStatsRxRate2Retries      Counter64,
        wdsStatsRxRate5Bytes        Counter64,
        wdsStatsRxRate5Packets      Counter64,
        wdsStatsRxRate5Errors       Counter64,
        wdsStatsRxRate5Retries      Counter64,
        wdsStatsRxRate11Bytes       Counter64,
        wdsStatsRxRate11Packets     Counter64,
        wdsStatsRxRate11Errors      Counter64,
        wdsStatsRxRate11Retries     Counter64,
        wdsStatsRxRate6Bytes        Counter64,
        wdsStatsRxRate6Packets      Counter64,
        wdsStatsRxRate6Errors       Counter64,
        wdsStatsRxRate6Retries      Counter64,
        wdsStatsRxRate9Bytes        Counter64,
        wdsStatsRxRate9Packets      Counter64,
        wdsStatsRxRate9Errors       Counter64,
        wdsStatsRxRate9Retries      Counter64,
        wdsStatsRxRate12Bytes       Counter64,
        wdsStatsRxRate12Packets     Counter64,
        wdsStatsRxRate12Errors      Counter64,
        wdsStatsRxRate12Retries     Counter64,
        wdsStatsRxRate18Bytes       Counter64,
        wdsStatsRxRate18Packets     Counter64,
        wdsStatsRxRate18Errors      Counter64,
        wdsStatsRxRate18Retries     Counter64,
        wdsStatsRxRate24Bytes       Counter64,
        wdsStatsRxRate24Packets     Counter64,
        wdsStatsRxRate24Errors      Counter64,
        wdsStatsRxRate24Retries     Counter64,
        wdsStatsRxRate36Bytes       Counter64,
        wdsStatsRxRate36Packets     Counter64,
        wdsStatsRxRate36Errors      Counter64,
        wdsStatsRxRate36Retries     Counter64,
        wdsStatsRxRate48Bytes       Counter64,
        wdsStatsRxRate48Packets     Counter64,
        wdsStatsRxRate48Errors      Counter64,
        wdsStatsRxRate48Retries     Counter64,
        wdsStatsRxRate54Bytes       Counter64,
        wdsStatsRxRate54Packets     Counter64,
        wdsStatsRxRate54Errors      Counter64,
        wdsStatsRxRate54Retries     Counter64,
        wdsStatsTxBytes             Counter64,
        wdsStatsTxPackets           Counter64,
        wdsStatsTxErrors            Counter64,
        wdsStatsTxRetries           Counter64,
        wdsStatsTxRate1Bytes        Counter64,
        wdsStatsTxRate1Packets      Counter64,
        wdsStatsTxRate1Errors       Counter64,
        wdsStatsTxRate1Retries      Counter64,
        wdsStatsTxRate2Bytes        Counter64,
        wdsStatsTxRate2Packets      Counter64,
        wdsStatsTxRate2Errors       Counter64,
        wdsStatsTxRate2Retries      Counter64,
        wdsStatsTxRate5Bytes        Counter64,
        wdsStatsTxRate5Packets      Counter64,
        wdsStatsTxRate5Errors       Counter64,
        wdsStatsTxRate5Retries      Counter64,
        wdsStatsTxRate11Bytes       Counter64,
        wdsStatsTxRate11Packets     Counter64,
        wdsStatsTxRate11Errors      Counter64,
        wdsStatsTxRate11Retries     Counter64,
        wdsStatsTxRate6Bytes        Counter64,
        wdsStatsTxRate6Packets      Counter64,
        wdsStatsTxRate6Errors       Counter64,
        wdsStatsTxRate6Retries      Counter64,
        wdsStatsTxRate9Bytes        Counter64,
        wdsStatsTxRate9Packets      Counter64,
        wdsStatsTxRate9Errors       Counter64,
        wdsStatsTxRate9Retries      Counter64,
        wdsStatsTxRate12Bytes       Counter64,
        wdsStatsTxRate12Packets     Counter64,
        wdsStatsTxRate12Errors      Counter64,
        wdsStatsTxRate12Retries     Counter64,
        wdsStatsTxRate18Bytes       Counter64,
        wdsStatsTxRate18Packets     Counter64,
        wdsStatsTxRate18Errors      Counter64,
        wdsStatsTxRate18Retries     Counter64,
        wdsStatsTxRate24Bytes       Counter64,
        wdsStatsTxRate24Packets     Counter64,
        wdsStatsTxRate24Errors      Counter64,
        wdsStatsTxRate24Retries     Counter64,
        wdsStatsTxRate36Bytes       Counter64,
        wdsStatsTxRate36Packets     Counter64,
        wdsStatsTxRate36Errors      Counter64,
        wdsStatsTxRate36Retries     Counter64,
        wdsStatsTxRate48Bytes       Counter64,
        wdsStatsTxRate48Packets     Counter64,
        wdsStatsTxRate48Errors      Counter64,
        wdsStatsTxRate48Retries     Counter64,
        wdsStatsTxRate54Bytes       Counter64,
        wdsStatsTxRate54Packets     Counter64,
        wdsStatsTxRate54Errors      Counter64,
        wdsStatsTxRate54Retries     Counter64
    }

    wdsStatsIndex OBJECT-TYPE
        SYNTAX          Integer32
        MAX-ACCESS      not-accessible
        STATUS          current
        DESCRIPTION
            "WDS link statistics index"
        ::= { wdsStatsEntry 1 }

    wdsStatsLinkName OBJECT-TYPE
        SYNTAX          DisplayString
        MAX-ACCESS      read-only
        STATUS          current
        DESCRIPTION
            "Name of the WDS lnk"
        ::= { wdsStatsEntry 2 }

    wdsStatsRxBytes OBJECT-TYPE
        SYNTAX          Counter64
        MAX-ACCESS      read-only
        STATUS          current
        DESCRIPTION
            "Bytes received"
        ::= { wdsStatsEntry 3 }

    wdsStatsRxPackets OBJECT-TYPE
        SYNTAX          Counter64
        MAX-ACCESS      read-only
        STATUS          current
        DESCRIPTION
            "Packets received"
        ::= { wdsStatsEntry 4 }

    wdsStatsRxErrors OBJECT-TYPE
        SYNTAX          Counter64
        MAX-ACCESS      read-only
        STATUS          current
        DESCRIPTION
            "Rx errors"
        ::= { wdsStatsEntry 5 }

    wdsStatsRxRetries OBJECT-TYPE
        SYNTAX          Counter64
        MAX-ACCESS      read-only
        STATUS          current
        DESCRIPTION
            "Rx retries"
        ::= { wdsStatsEntry 6 }

    wdsStatsRxRate1Bytes OBJECT-TYPE
        SYNTAX          Counter64
        MAX-ACCESS      read-only
        STATUS          current
        DESCRIPTION
            "Bytes received at rate 1Mbps"
        ::= { wdsStatsEntry 7 }

    wdsStatsRxRate1Packets OBJECT-TYPE
        SYNTAX          Counter64
        MAX-ACCESS      read-only
        STATUS          current
        DESCRIPTION
            "Packets received at rate 1Mbps"
        ::= { wdsStatsEntry 8 }

    wdsStatsRxRate1Errors OBJECT-TYPE
        SYNTAX          Counter64
        MAX-ACCESS      read-only
        STATUS          current
        DESCRIPTION
            "Rx errors at rate 1Mbps"
        ::= { wdsStatsEntry 9 }

    wdsStatsRxRate1Retries OBJECT-TYPE
        SYNTAX          Counter64
        MAX-ACCESS      read-only
        STATUS          current
        DESCRIPTION
            "Rx retries at rate 1Mbps"
        ::= { wdsStatsEntry 10 }

    wdsStatsRxRate2Bytes OBJECT-TYPE
        SYNTAX          Counter64
        MAX-ACCESS      read-only
        STATUS          current
        DESCRIPTION
            "Bytes received at rate 2Mbps"
        ::= { wdsStatsEntry 11 }

    wdsStatsRxRate2Packets OBJECT-TYPE
        SYNTAX          Counter64
        MAX-ACCESS      read-only
        STATUS          current
        DESCRIPTION
            "Packets received at rate 2Mbps"
        ::= { wdsStatsEntry 12 }

    wdsStatsRxRate2Errors OBJECT-TYPE
        SYNTAX          Counter64
        MAX-ACCESS      read-only
        STATUS          current
        DESCRIPTION
            "Rx errors at rate 2Mbps"
        ::= { wdsStatsEntry 13 }

    wdsStatsRxRate2Retries OBJECT-TYPE
        SYNTAX          Counter64
        MAX-ACCESS      read-only
        STATUS          current
        DESCRIPTION
            "Rx retries at rate 2Mbps"
        ::= { wdsStatsEntry 14 }

    wdsStatsRxRate5Bytes OBJECT-TYPE
        SYNTAX          Counter64
        MAX-ACCESS      read-only
        STATUS          current
        DESCRIPTION
            "Bytes received at rate 5.5Mbps"
        ::= { wdsStatsEntry 15 }

    wdsStatsRxRate5Packets OBJECT-TYPE
        SYNTAX          Counter64
        MAX-ACCESS      read-only
        STATUS          current
        DESCRIPTION
            "Packets received at rate 5.5Mbps"
        ::= { wdsStatsEntry 16 }

    wdsStatsRxRate5Errors OBJECT-TYPE
        SYNTAX          Counter64
        MAX-ACCESS      read-only
        STATUS          current
        DESCRIPTION
            "Rx errors at rate 5.5Mbps"
        ::= { wdsStatsEntry 17 }

    wdsStatsRxRate5Retries OBJECT-TYPE
        SYNTAX          Counter64
        MAX-ACCESS      read-only
        STATUS          current
        DESCRIPTION
            "Rx retries at rate 5.5Mbps"
        ::= { wdsStatsEntry 18 }

    wdsStatsRxRate11Bytes OBJECT-TYPE
        SYNTAX          Counter64
        MAX-ACCESS      read-only
        STATUS          current
        DESCRIPTION
            "Bytes received at rate 11Mbps"
        ::= { wdsStatsEntry 19 }

    wdsStatsRxRate11Packets OBJECT-TYPE
        SYNTAX          Counter64
        MAX-ACCESS      read-only
        STATUS          current
        DESCRIPTION
            "Packets received at rate 11Mbps"
        ::= { wdsStatsEntry 20 }

    wdsStatsRxRate11Errors OBJECT-TYPE
        SYNTAX          Counter64
        MAX-ACCESS      read-only
        STATUS          current
        DESCRIPTION
            "Rx errors at rate 11Mbps"
        ::= { wdsStatsEntry 21 }

    wdsStatsRxRate11Retries OBJECT-TYPE
        SYNTAX          Counter64
        MAX-ACCESS      read-only
        STATUS          current
        DESCRIPTION
            "Rx retries at rate 11Mbps"
        ::= { wdsStatsEntry 22 }

    wdsStatsRxRate6Bytes OBJECT-TYPE
        SYNTAX          Counter64
        MAX-ACCESS      read-only
        STATUS          current
        DESCRIPTION
            "Bytes received at rate 6Mbps"
        ::= { wdsStatsEntry 23 }

    wdsStatsRxRate6Packets OBJECT-TYPE
        SYNTAX          Counter64
        MAX-ACCESS      read-only
        STATUS          current
        DESCRIPTION
            "Packets received at rate 6Mbps"
        ::= { wdsStatsEntry 24 }

    wdsStatsRxRate6Errors OBJECT-TYPE
        SYNTAX          Counter64
        MAX-ACCESS      read-only
        STATUS          current
        DESCRIPTION
            "Rx errors at rate 6Mbps"
        ::= { wdsStatsEntry 25 }

    wdsStatsRxRate6Retries OBJECT-TYPE
        SYNTAX          Counter64
        MAX-ACCESS      read-only
        STATUS          current
        DESCRIPTION
            "Rx retries at rate 6Mbps"
        ::= { wdsStatsEntry 26 }

    wdsStatsRxRate9Bytes OBJECT-TYPE
        SYNTAX          Counter64
        MAX-ACCESS      read-only
        STATUS          current
        DESCRIPTION
            "Bytes received at rate 9Mbps"
        ::= { wdsStatsEntry 27 }

    wdsStatsRxRate9Packets OBJECT-TYPE
        SYNTAX          Counter64
        MAX-ACCESS      read-only
        STATUS          current
        DESCRIPTION
            "Packets received at rate 9Mbps"
        ::= { wdsStatsEntry 28 }

    wdsStatsRxRate9Errors OBJECT-TYPE
        SYNTAX          Counter64
        MAX-ACCESS      read-only
        STATUS          current
        DESCRIPTION
            "Rx errors at rate 9Mbps"
        ::= { wdsStatsEntry 29 }

    wdsStatsRxRate9Retries OBJECT-TYPE
        SYNTAX          Counter64
        MAX-ACCESS      read-only
        STATUS          current
        DESCRIPTION
            "Rx retries at rate 9Mbps"
        ::= { wdsStatsEntry 30 }

    wdsStatsRxRate12Bytes OBJECT-TYPE
        SYNTAX          Counter64
        MAX-ACCESS      read-only
        STATUS          current
        DESCRIPTION
            "Bytes received at rate 12Mbps"
        ::= { wdsStatsEntry 31 }

    wdsStatsRxRate12Packets OBJECT-TYPE
        SYNTAX          Counter64
        MAX-ACCESS      read-only
        STATUS          current
        DESCRIPTION
            "Packets received at rate 12Mbps"
        ::= { wdsStatsEntry 32 }

    wdsStatsRxRate12Errors OBJECT-TYPE
        SYNTAX          Counter64
        MAX-ACCESS      read-only
        STATUS          current
        DESCRIPTION
            "Rx errors at rate 12Mbps"
        ::= { wdsStatsEntry 33 }

    wdsStatsRxRate12Retries OBJECT-TYPE
        SYNTAX          Counter64
        MAX-ACCESS      read-only
        STATUS          current
        DESCRIPTION
            "Rx retries at rate 12Mbps"
        ::= { wdsStatsEntry 34 }

    wdsStatsRxRate18Bytes OBJECT-TYPE
        SYNTAX          Counter64
        MAX-ACCESS      read-only
        STATUS          current
        DESCRIPTION
            "Bytes received at rate 18Mbps"
        ::= { wdsStatsEntry 35 }

    wdsStatsRxRate18Packets OBJECT-TYPE
        SYNTAX          Counter64
        MAX-ACCESS      read-only
        STATUS          current
        DESCRIPTION
            "Packets received at rate 18Mbps"
        ::= { wdsStatsEntry 36 }

    wdsStatsRxRate18Errors OBJECT-TYPE
        SYNTAX          Counter64
        MAX-ACCESS      read-only
        STATUS          current
        DESCRIPTION
            "Rx errors at rate 18Mbps"
        ::= { wdsStatsEntry 37 }

    wdsStatsRxRate18Retries OBJECT-TYPE
        SYNTAX          Counter64
        MAX-ACCESS      read-only
        STATUS          current
        DESCRIPTION
            "Rx retries at rate 18Mbps"
        ::= { wdsStatsEntry 38 }

    wdsStatsRxRate24Bytes OBJECT-TYPE
        SYNTAX          Counter64
        MAX-ACCESS      read-only
        STATUS          current
        DESCRIPTION
            "Bytes received at rate 24Mbps"
        ::= { wdsStatsEntry 39 }

    wdsStatsRxRate24Packets OBJECT-TYPE
        SYNTAX          Counter64
        MAX-ACCESS      read-only
        STATUS          current
        DESCRIPTION
            "Packets received at rate 24Mbps"
        ::= { wdsStatsEntry 40 }

    wdsStatsRxRate24Errors OBJECT-TYPE
        SYNTAX          Counter64
        MAX-ACCESS      read-only
        STATUS          current
        DESCRIPTION
            "Rx errors at rate 24Mbps"
        ::= { wdsStatsEntry 41 }

    wdsStatsRxRate24Retries OBJECT-TYPE
        SYNTAX          Counter64
        MAX-ACCESS      read-only
        STATUS          current
        DESCRIPTION
            "Rx retries at rate 24Mbps"
        ::= { wdsStatsEntry 42 }

    wdsStatsRxRate36Bytes OBJECT-TYPE
        SYNTAX          Counter64
        MAX-ACCESS      read-only
        STATUS          current
        DESCRIPTION
            "Bytes received at rate 36Mbps"
        ::= { wdsStatsEntry 43 }

    wdsStatsRxRate36Packets OBJECT-TYPE
        SYNTAX          Counter64
        MAX-ACCESS      read-only
        STATUS          current
        DESCRIPTION
            "Packets received at rate 36Mbps"
        ::= { wdsStatsEntry 44 }

    wdsStatsRxRate36Errors OBJECT-TYPE
        SYNTAX          Counter64
        MAX-ACCESS      read-only
        STATUS          current
        DESCRIPTION
            "Rx errors at rate 36Mbps"
        ::= { wdsStatsEntry 45 }

    wdsStatsRxRate36Retries OBJECT-TYPE
        SYNTAX          Counter64
        MAX-ACCESS      read-only
        STATUS          current
        DESCRIPTION
            "Rx retries at rate 36Mbps"
        ::= { wdsStatsEntry 46 }

    wdsStatsRxRate48Bytes OBJECT-TYPE
        SYNTAX          Counter64
        MAX-ACCESS      read-only
        STATUS          current
        DESCRIPTION
            "Bytes received at rate 48Mbps"
        ::= { wdsStatsEntry 47 }

    wdsStatsRxRate48Packets OBJECT-TYPE
        SYNTAX          Counter64
        MAX-ACCESS      read-only
        STATUS          current
        DESCRIPTION
            "Packets received at rate 48Mbps"
        ::= { wdsStatsEntry 48 }

    wdsStatsRxRate48Errors OBJECT-TYPE
        SYNTAX          Counter64
        MAX-ACCESS      read-only
        STATUS          current
        DESCRIPTION
            "Rx errors at rate 48Mbps"
        ::= { wdsStatsEntry 49 }

    wdsStatsRxRate48Retries OBJECT-TYPE
        SYNTAX          Counter64
        MAX-ACCESS      read-only
        STATUS          current
        DESCRIPTION
            "Rx retries at rate 48Mbps"
        ::= { wdsStatsEntry 50 }

    wdsStatsRxRate54Bytes OBJECT-TYPE
        SYNTAX          Counter64
        MAX-ACCESS      read-only
        STATUS          current
        DESCRIPTION
            "Bytes received at rate 54Mbps"
        ::= { wdsStatsEntry 51 }

    wdsStatsRxRate54Packets OBJECT-TYPE
        SYNTAX          Counter64
        MAX-ACCESS      read-only
        STATUS          current
        DESCRIPTION
            "Packets received at rate 54Mbps"
        ::= { wdsStatsEntry 52 }

    wdsStatsRxRate54Errors OBJECT-TYPE
        SYNTAX          Counter64
        MAX-ACCESS      read-only
        STATUS          current
        DESCRIPTION
            "Rx errors at rate 54Mbps"
        ::= { wdsStatsEntry 53 }

    wdsStatsRxRate54Retries OBJECT-TYPE
        SYNTAX          Counter64
        MAX-ACCESS      read-only
        STATUS          current
        DESCRIPTION
            "Rx retries at rate 54Mbps"
        ::= { wdsStatsEntry 54 }

    wdsStatsTxBytes OBJECT-TYPE
        SYNTAX          Counter64
        MAX-ACCESS      read-only
        STATUS          current
        DESCRIPTION
            "Bytes transmitted"
        ::= { wdsStatsEntry 55 }

    wdsStatsTxPackets OBJECT-TYPE
        SYNTAX          Counter64
        MAX-ACCESS      read-only
        STATUS          current
        DESCRIPTION
            "Packets transmitted"
        ::= { wdsStatsEntry 56 }

    wdsStatsTxErrors OBJECT-TYPE
        SYNTAX          Counter64
        MAX-ACCESS      read-only
        STATUS          current
        DESCRIPTION
            "Tx errors"
        ::= { wdsStatsEntry 57 }

    wdsStatsTxRetries OBJECT-TYPE
        SYNTAX          Counter64
        MAX-ACCESS      read-only
        STATUS          current
        DESCRIPTION
            "Tx retries"
        ::= { wdsStatsEntry 58 }

    wdsStatsTxRate1Bytes OBJECT-TYPE
        SYNTAX          Counter64
        MAX-ACCESS      read-only
        STATUS          current
        DESCRIPTION
            "Bytes transmitted at rate 1Mbps"
        ::= { wdsStatsEntry 59 }

    wdsStatsTxRate1Packets OBJECT-TYPE
        SYNTAX          Counter64
        MAX-ACCESS      read-only
        STATUS          current
        DESCRIPTION
            "Packets transmitted at rate 1Mbps"
        ::= { wdsStatsEntry 60 }

    wdsStatsTxRate1Errors OBJECT-TYPE
        SYNTAX          Counter64
        MAX-ACCESS      read-only
        STATUS          current
        DESCRIPTION
            "Tx errors at rate 1Mbps"
        ::= { wdsStatsEntry 61 }

    wdsStatsTxRate1Retries OBJECT-TYPE
        SYNTAX          Counter64
        MAX-ACCESS      read-only
        STATUS          current
        DESCRIPTION
            "Tx retries at rate 1Mbps"
        ::= { wdsStatsEntry 62 }

    wdsStatsTxRate2Bytes OBJECT-TYPE
        SYNTAX          Counter64
        MAX-ACCESS      read-only
        STATUS          current
        DESCRIPTION
            "Bytes transmitted at rate 2Mbps"
        ::= { wdsStatsEntry 63 }

    wdsStatsTxRate2Packets OBJECT-TYPE
        SYNTAX          Counter64
        MAX-ACCESS      read-only
        STATUS          current
        DESCRIPTION
            "Packets transmitted at rate 2Mbps"
        ::= { wdsStatsEntry 64 }

    wdsStatsTxRate2Errors OBJECT-TYPE
        SYNTAX          Counter64
        MAX-ACCESS      read-only
        STATUS          current
        DESCRIPTION
            "Tx errors at rate 2Mbps"
        ::= { wdsStatsEntry 65 }

    wdsStatsTxRate2Retries OBJECT-TYPE
        SYNTAX          Counter64
        MAX-ACCESS      read-only
        STATUS          current
        DESCRIPTION
            "Tx retries at rate 2Mbps"
        ::= { wdsStatsEntry 66 }

    wdsStatsTxRate5Bytes OBJECT-TYPE
        SYNTAX          Counter64
        MAX-ACCESS      read-only
        STATUS          current
        DESCRIPTION
            "Bytes transmitted at rate 5.5Mbps"
        ::= { wdsStatsEntry 67 }

    wdsStatsTxRate5Packets OBJECT-TYPE
        SYNTAX          Counter64
        MAX-ACCESS      read-only
        STATUS          current
        DESCRIPTION
            "Packets transmitted at rate 5.5Mbps"
        ::= { wdsStatsEntry 68 }

    wdsStatsTxRate5Errors OBJECT-TYPE
        SYNTAX          Counter64
        MAX-ACCESS      read-only
        STATUS          current
        DESCRIPTION
            "Tx errors at rate 5.5Mbps"
        ::= { wdsStatsEntry 69 }

    wdsStatsTxRate5Retries OBJECT-TYPE
        SYNTAX          Counter64
        MAX-ACCESS      read-only
        STATUS          current
        DESCRIPTION
            "Tx retries at rate 5.5Mbps"
        ::= { wdsStatsEntry 70 }

    wdsStatsTxRate11Bytes OBJECT-TYPE
        SYNTAX          Counter64
        MAX-ACCESS      read-only
        STATUS          current
        DESCRIPTION
            "Bytes transmitted at rate 11Mbps"
        ::= { wdsStatsEntry 71 }

    wdsStatsTxRate11Packets OBJECT-TYPE
        SYNTAX          Counter64
        MAX-ACCESS      read-only
        STATUS          current
        DESCRIPTION
            "Packets transmitted at rate 11Mbps"
        ::= { wdsStatsEntry 72 }

    wdsStatsTxRate11Errors OBJECT-TYPE
        SYNTAX          Counter64
        MAX-ACCESS      read-only
        STATUS          current
        DESCRIPTION
            "Tx errors at rate 11Mbps"
        ::= { wdsStatsEntry 73 }

    wdsStatsTxRate11Retries OBJECT-TYPE
        SYNTAX          Counter64
        MAX-ACCESS      read-only
        STATUS          current
        DESCRIPTION
            "Tx retries at rate 11Mbps"
        ::= { wdsStatsEntry 74 }

    wdsStatsTxRate6Bytes OBJECT-TYPE
        SYNTAX          Counter64
        MAX-ACCESS      read-only
        STATUS          current
        DESCRIPTION
            "Bytes transmitted at rate 6Mbps"
        ::= { wdsStatsEntry 75 }

    wdsStatsTxRate6Packets OBJECT-TYPE
        SYNTAX          Counter64
        MAX-ACCESS      read-only
        STATUS          current
        DESCRIPTION
            "Packets transmitted at rate 6Mbps"
        ::= { wdsStatsEntry 76 }

    wdsStatsTxRate6Errors OBJECT-TYPE
        SYNTAX          Counter64
        MAX-ACCESS      read-only
        STATUS          current
        DESCRIPTION
            "Tx errors at rate 6Mbps"
        ::= { wdsStatsEntry 77 }

    wdsStatsTxRate6Retries OBJECT-TYPE
        SYNTAX          Counter64
        MAX-ACCESS      read-only
        STATUS          current
        DESCRIPTION
            "Tx retries at rate 6Mbps"
        ::= { wdsStatsEntry 78 }

    wdsStatsTxRate9Bytes OBJECT-TYPE
        SYNTAX          Counter64
        MAX-ACCESS      read-only
        STATUS          current
        DESCRIPTION
            "Bytes transmitted at rate 9Mbps"
        ::= { wdsStatsEntry 79 }

    wdsStatsTxRate9Packets OBJECT-TYPE
        SYNTAX          Counter64
        MAX-ACCESS      read-only
        STATUS          current
        DESCRIPTION
            "Packets transmitted at rate 9Mbps"
        ::= { wdsStatsEntry 80 }

    wdsStatsTxRate9Errors OBJECT-TYPE
        SYNTAX          Counter64
        MAX-ACCESS      read-only
        STATUS          current
        DESCRIPTION
            "Tx errors at rate 9Mbps"
        ::= { wdsStatsEntry 81 }

    wdsStatsTxRate9Retries OBJECT-TYPE
        SYNTAX          Counter64
        MAX-ACCESS      read-only
        STATUS          current
        DESCRIPTION
            "Tx retries at rate 9Mbps"
        ::= { wdsStatsEntry 82 }

    wdsStatsTxRate12Bytes OBJECT-TYPE
        SYNTAX          Counter64
        MAX-ACCESS      read-only
        STATUS          current
        DESCRIPTION
            "Bytes transmitted at rate 12Mbps"
        ::= { wdsStatsEntry 83 }

    wdsStatsTxRate12Packets OBJECT-TYPE
        SYNTAX          Counter64
        MAX-ACCESS      read-only
        STATUS          current
        DESCRIPTION
            "Packets transmitted at rate 12Mbps"
        ::= { wdsStatsEntry 84 }

    wdsStatsTxRate12Errors OBJECT-TYPE
        SYNTAX          Counter64
        MAX-ACCESS      read-only
        STATUS          current
        DESCRIPTION
            "Tx errors at rate 12Mbps"
        ::= { wdsStatsEntry 85 }

    wdsStatsTxRate12Retries OBJECT-TYPE
        SYNTAX          Counter64
        MAX-ACCESS      read-only
        STATUS          current
        DESCRIPTION
            "Tx retries at rate 12Mbps"
        ::= { wdsStatsEntry 86 }

    wdsStatsTxRate18Bytes OBJECT-TYPE
        SYNTAX          Counter64
        MAX-ACCESS      read-only
        STATUS          current
        DESCRIPTION
            "Bytes transmitted at rate 18Mbps"
        ::= { wdsStatsEntry 87 }

    wdsStatsTxRate18Packets OBJECT-TYPE
        SYNTAX          Counter64
        MAX-ACCESS      read-only
        STATUS          current
        DESCRIPTION
            "Packets transmitted at rate 18Mbps"
        ::= { wdsStatsEntry 88 }

    wdsStatsTxRate18Errors OBJECT-TYPE
        SYNTAX          Counter64
        MAX-ACCESS      read-only
        STATUS          current
        DESCRIPTION
            "Tx errors at rate 18Mbps"
        ::= { wdsStatsEntry 89 }

    wdsStatsTxRate18Retries OBJECT-TYPE
        SYNTAX          Counter64
        MAX-ACCESS      read-only
        STATUS          current
        DESCRIPTION
            "Tx retries at rate 18Mbps"
        ::= { wdsStatsEntry 90 }

    wdsStatsTxRate24Bytes OBJECT-TYPE
        SYNTAX          Counter64
        MAX-ACCESS      read-only
        STATUS          current
        DESCRIPTION
            "Bytes transmitted at rate 24Mbps"
        ::= { wdsStatsEntry 91 }

    wdsStatsTxRate24Packets OBJECT-TYPE
        SYNTAX          Counter64
        MAX-ACCESS      read-only
        STATUS          current
        DESCRIPTION
            "Packets transmitted at rate 24Mbps"
        ::= { wdsStatsEntry 92 }

    wdsStatsTxRate24Errors OBJECT-TYPE
        SYNTAX          Counter64
        MAX-ACCESS      read-only
        STATUS          current
        DESCRIPTION
            "Tx errors at rate 24Mbps"
        ::= { wdsStatsEntry 93 }

    wdsStatsTxRate24Retries OBJECT-TYPE
        SYNTAX          Counter64
        MAX-ACCESS      read-only
        STATUS          current
        DESCRIPTION
            "Tx retries at rate 24Mbps"
        ::= { wdsStatsEntry 94 }

    wdsStatsTxRate36Bytes OBJECT-TYPE
        SYNTAX          Counter64
        MAX-ACCESS      read-only
        STATUS          current
        DESCRIPTION
            "Bytes transmitted at rate 36Mbps"
        ::= { wdsStatsEntry 95 }

    wdsStatsTxRate36Packets OBJECT-TYPE
        SYNTAX          Counter64
        MAX-ACCESS      read-only
        STATUS          current
        DESCRIPTION
            "Packets transmitted at rate 36Mbps"
        ::= { wdsStatsEntry 96 }

    wdsStatsTxRate36Errors OBJECT-TYPE
        SYNTAX          Counter64
        MAX-ACCESS      read-only
        STATUS          current
        DESCRIPTION
            "Tx errors at rate 36Mbps"
        ::= { wdsStatsEntry 97 }

    wdsStatsTxRate36Retries OBJECT-TYPE
        SYNTAX          Counter64
        MAX-ACCESS      read-only
        STATUS          current
        DESCRIPTION
            "Tx retries at rate 36Mbps"
        ::= { wdsStatsEntry 98 }

    wdsStatsTxRate48Bytes OBJECT-TYPE
        SYNTAX          Counter64
        MAX-ACCESS      read-only
        STATUS          current
        DESCRIPTION
            "Bytes transmitted at rate 48Mbps"
        ::= { wdsStatsEntry 99 }

    wdsStatsTxRate48Packets OBJECT-TYPE
        SYNTAX          Counter64
        MAX-ACCESS      read-only
        STATUS          current
        DESCRIPTION
            "Packets transmitted at rate 48Mbps"
        ::= { wdsStatsEntry 100 }

    wdsStatsTxRate48Errors OBJECT-TYPE
        SYNTAX          Counter64
        MAX-ACCESS      read-only
        STATUS          current
        DESCRIPTION
            "Tx errors at rate 48Mbps"
        ::= { wdsStatsEntry 101 }

    wdsStatsTxRate48Retries OBJECT-TYPE
        SYNTAX          Counter64
        MAX-ACCESS      read-only
        STATUS          current
        DESCRIPTION
            "Tx retries at rate 48Mbps"
        ::= { wdsStatsEntry 102 }

    wdsStatsTxRate54Bytes OBJECT-TYPE
        SYNTAX          Counter64
        MAX-ACCESS      read-only
        STATUS          current
        DESCRIPTION
            "Bytes transmitted at rate 54Mbps"
        ::= { wdsStatsEntry 103 }

    wdsStatsTxRate54Packets OBJECT-TYPE
        SYNTAX          Counter64
        MAX-ACCESS      read-only
        STATUS          current
        DESCRIPTION
            "Packets transmitted at rate 54Mbps"
        ::= { wdsStatsEntry 104 }

    wdsStatsTxRate54Errors OBJECT-TYPE
        SYNTAX          Counter64
        MAX-ACCESS      read-only
        STATUS          current
        DESCRIPTION
            "Tx errors at rate 54Mbps"
        ::= { wdsStatsEntry 105 }

    wdsStatsTxRate54Retries OBJECT-TYPE
        SYNTAX          Counter64
        MAX-ACCESS      read-only
        STATUS          current
        DESCRIPTION
            "Tx retries at rate 54Mbps"
        ::= { wdsStatsEntry 106 }

    spectrumAnalysisTable OBJECT-TYPE
        SYNTAX          SEQUENCE OF SpectrumAnalysisEntry
        MAX-ACCESS      not-accessible
        STATUS          current
        DESCRIPTION
            "Spectrum analysis information table"
        ::= { statistics 6 }

    spectrumAnalysisEntry OBJECT-TYPE
        SYNTAX          SpectrumAnalysisEntry
        MAX-ACCESS      not-accessible
        STATUS          current
        DESCRIPTION
            "Table entry for spectrum analysis information"
        INDEX       { spectrumAnalysisIndex }
        ::= { spectrumAnalysisTable 1 }

    SpectrumAnalysisEntry ::= SEQUENCE {
        spectrumAnalysisIndex                   Integer32,
        spectrumAnalysisChannel                 Integer32,
        spectrumAnalysisPackets                 Integer32,
        spectrumAnalysisBytes                   Integer32,
        spectrumAnalysisErrorRate               Integer32,
        spectrumAnalysisAverageDataRate         Integer32,
        spectrumAnalysisAverageRSSI             Integer32,
        spectrumAnalysisSignalToNoiseRatio      Integer32,
        spectrumAnalysisNoiseFloor              Integer32,
        spectrumAnalysisDot11Busy               Integer32,
        spectrumAnalysisNoise                   Integer32
    }

    spectrumAnalysisIndex OBJECT-TYPE
        SYNTAX          Integer32
        MAX-ACCESS      not-accessible
        STATUS          current
        DESCRIPTION
            "Spectrum analysis information index"
        ::= { spectrumAnalysisEntry 1 }

    spectrumAnalysisChannel OBJECT-TYPE
        SYNTAX          Integer32
        MAX-ACCESS      read-only
        STATUS          current
        DESCRIPTION
            "Channel number"
        ::= { spectrumAnalysisEntry 2 }

    spectrumAnalysisPackets OBJECT-TYPE
        SYNTAX          Integer32
        MAX-ACCESS      read-only
        STATUS          current
        DESCRIPTION
            "Packets per second"
        ::= { spectrumAnalysisEntry 3 }

    spectrumAnalysisBytes OBJECT-TYPE
        SYNTAX          Integer32
        MAX-ACCESS      read-only
        STATUS          current
        DESCRIPTION
            "Bytes per second"
        ::= { spectrumAnalysisEntry 4 }

    spectrumAnalysisErrorRate OBJECT-TYPE
        SYNTAX          Integer32
        MAX-ACCESS      read-only
        STATUS          current
        DESCRIPTION
            "Error rate (in percent)"
        ::= { spectrumAnalysisEntry 5 }

    spectrumAnalysisAverageDataRate OBJECT-TYPE
        SYNTAX          Integer32
        MAX-ACCESS      read-only
        STATUS          current
        DESCRIPTION
            "Average data rate (in Mbps)"
        ::= { spectrumAnalysisEntry 6 }

    spectrumAnalysisAverageRSSI OBJECT-TYPE
        SYNTAX          Integer32
        MAX-ACCESS      read-only
        STATUS          current
        DESCRIPTION
            "Average RSSI"
        ::= { spectrumAnalysisEntry 7 }

    spectrumAnalysisSignalToNoiseRatio OBJECT-TYPE
        SYNTAX          Integer32
        MAX-ACCESS      read-only
        STATUS          current
        DESCRIPTION
            "Signal to noise ratio"
        ::= { spectrumAnalysisEntry 8 }

    spectrumAnalysisNoiseFloor OBJECT-TYPE
        SYNTAX          Integer32
        MAX-ACCESS      read-only
        STATUS          current
        DESCRIPTION
            "Noise floor"
        ::= { spectrumAnalysisEntry 9 }

    spectrumAnalysisDot11Busy OBJECT-TYPE
        SYNTAX          Integer32
        MAX-ACCESS      read-only
        STATUS          current
        DESCRIPTION
            "802.11 medium busy (in percent)"
        ::= { spectrumAnalysisEntry 10 }

    spectrumAnalysisNoise OBJECT-TYPE
        SYNTAX          Integer32
        MAX-ACCESS      read-only
        STATUS          current
        DESCRIPTION
            "Noise (in percent)"
        ::= { spectrumAnalysisEntry 11 }

    realtimeMonitorTable OBJECT-TYPE
        SYNTAX          SEQUENCE OF RealtimeMonitorEntry
        MAX-ACCESS      not-accessible
        STATUS          current
        DESCRIPTION
            "Real time IAP information table"
        ::= { statistics 7 }

    realtimeMonitorEntry OBJECT-TYPE
        SYNTAX          RealtimeMonitorEntry
        MAX-ACCESS      not-accessible
        STATUS          current
        DESCRIPTION
            "Table entry for real time IAP information"
        INDEX       { realtimeMonitorIndex }
        ::= { realtimeMonitorTable 1 }

    RealtimeMonitorEntry ::= SEQUENCE {
        realtimeMonitorIndex                    Integer32,
        realtimeMonitorIfaceName                DisplayString,
        realtimeMonitorChannel                  Integer32,
        realtimeMonitorPackets                  Integer32,
        realtimeMonitorBytes                    Integer32,
        realtimeMonitorErrorRate                Integer32,
        realtimeMonitorAverageDataRate          Integer32,
        realtimeMonitorAverageRSSI              Integer32,
        realtimeMonitorSignalToNoiseRatio       Integer32,
        realtimeMonitorNoiseFloor               Integer32,
        realtimeMonitorDot11Busy                Integer32,
        realtimeMonitorNoise                    Integer32
    }

    realtimeMonitorIndex OBJECT-TYPE
        SYNTAX          Integer32
        MAX-ACCESS      not-accessible
        STATUS          current
        DESCRIPTION
            "Real time IAP information index"
        ::= { realtimeMonitorEntry 1 }

    realtimeMonitorIfaceName OBJECT-TYPE
        SYNTAX          DisplayString
        MAX-ACCESS      read-only
        STATUS          current
        DESCRIPTION
            "Interface name"
        ::= { realtimeMonitorEntry 2 }

    realtimeMonitorChannel OBJECT-TYPE
        SYNTAX          Integer32
        MAX-ACCESS      read-only
        STATUS          current
        DESCRIPTION
            "Channel number"
        ::= { realtimeMonitorEntry 3 }

    realtimeMonitorPackets OBJECT-TYPE
        SYNTAX          Integer32
        MAX-ACCESS      read-only
        STATUS          current
        DESCRIPTION
            "Packets per second"
        ::= { realtimeMonitorEntry 4 }

    realtimeMonitorBytes OBJECT-TYPE
        SYNTAX          Integer32
        MAX-ACCESS      read-only
        STATUS          current
        DESCRIPTION
            "Bytes per second"
        ::= { realtimeMonitorEntry 5 }

    realtimeMonitorErrorRate OBJECT-TYPE
        SYNTAX          Integer32
        MAX-ACCESS      read-only
        STATUS          current
        DESCRIPTION
            "Error rate (in percent)"
        ::= { realtimeMonitorEntry 6 }

    realtimeMonitorAverageDataRate OBJECT-TYPE
        SYNTAX          Integer32
        MAX-ACCESS      read-only
        STATUS          current
        DESCRIPTION
            "Average data rate (in Mbps)"
        ::= { realtimeMonitorEntry 7 }

    realtimeMonitorAverageRSSI OBJECT-TYPE
        SYNTAX          Integer32
        MAX-ACCESS      read-only
        STATUS          current
        DESCRIPTION
            "Average RSSI"
        ::= { realtimeMonitorEntry 8 }

    realtimeMonitorSignalToNoiseRatio OBJECT-TYPE
        SYNTAX          Integer32
        MAX-ACCESS      read-only
        STATUS          current
        DESCRIPTION
            "Signal to noise ratio"
        ::= { realtimeMonitorEntry 9 }

    realtimeMonitorNoiseFloor OBJECT-TYPE
        SYNTAX          Integer32
        MAX-ACCESS      read-only
        STATUS          current
        DESCRIPTION
            "Noise floor"
        ::= { realtimeMonitorEntry 10 }

    realtimeMonitorDot11Busy OBJECT-TYPE
        SYNTAX          Integer32
        MAX-ACCESS      read-only
        STATUS          current
        DESCRIPTION
            "802.11 medium busy (in percent)"
        ::= { realtimeMonitorEntry 11 }

    realtimeMonitorNoise OBJECT-TYPE
        SYNTAX          Integer32
        MAX-ACCESS      read-only
        STATUS          current
        DESCRIPTION
            "Noise (in percent)"
        ::= { realtimeMonitorEntry 12 }

    stationAppStatsTable OBJECT-TYPE
        SYNTAX          SEQUENCE OF StationAppStatsEntry
        MAX-ACCESS      not-accessible
        STATUS          current
        DESCRIPTION
            "Table of station application statistics"
        ::= { statistics 8 }

    stationAppStatsEntry OBJECT-TYPE
        SYNTAX          StationAppStatsEntry
        MAX-ACCESS      not-accessible
        STATUS          current
        DESCRIPTION
            "Table entry for station application statistics"
        INDEX       { stationAppStatsIndex }
        ::= { stationAppStatsTable 1 }

    StationAppStatsEntry ::= SEQUENCE {
        stationAppStatsIndex               Integer32,
        stationAppStatsMACAddress          DisplayString,
        stationAppStatsGuid                DisplayString,
        stationAppStatsTxPackets           Counter64,
        stationAppStatsRxPackets           Counter64,
        stationAppStatsTxBytes             Counter64,
        stationAppStatsRxBytes             Counter64,
        stationAppStatsTimePeriod          Counter32
    }

    stationAppStatsIndex OBJECT-TYPE
        SYNTAX          Integer32
        MAX-ACCESS      not-accessible
        STATUS          current
        DESCRIPTION
            "Station application statistics index"
        ::= { stationAppStatsEntry 1 }

    stationAppStatsMACAddress OBJECT-TYPE
        SYNTAX          DisplayString
        MAX-ACCESS      read-only
        STATUS          current
        DESCRIPTION
            "MAC address of the station"
        ::= { stationAppStatsEntry 2 }

    stationAppStatsGuid OBJECT-TYPE
        SYNTAX          DisplayString
        MAX-ACCESS      read-only
        STATUS          current
        DESCRIPTION
            "Global Unique ID of the application"
        ::= { stationAppStatsEntry 3 }

    stationAppStatsTxPackets OBJECT-TYPE
        SYNTAX          Counter64
        MAX-ACCESS      read-only
        STATUS          current
        DESCRIPTION
            "Packets transmitted"
        ::= { stationAppStatsEntry 4 }

    stationAppStatsRxPackets OBJECT-TYPE
        SYNTAX          Counter64
        MAX-ACCESS      read-only
        STATUS          current
        DESCRIPTION
            "Packets received"
        ::= { stationAppStatsEntry 5 }

    stationAppStatsTxBytes OBJECT-TYPE
        SYNTAX          Counter64
        MAX-ACCESS      read-only
        STATUS          current
        DESCRIPTION
            "Bytes transmitted"
        ::= { stationAppStatsEntry 6 }

    stationAppStatsRxBytes OBJECT-TYPE
        SYNTAX          Counter64
        MAX-ACCESS      read-only
        STATUS          current
        DESCRIPTION
            "Bytes received"
        ::= { stationAppStatsEntry 7 }

    stationAppStatsTimePeriod OBJECT-TYPE
        SYNTAX          Counter32
        MAX-ACCESS      read-only
        STATUS          current
        DESCRIPTION
            "Time period over which application stats were collected"
        ::= { stationAppStatsEntry 8 }

    stationAppCatStatsTable OBJECT-TYPE
        SYNTAX          SEQUENCE OF StationAppCatStatsEntry
        MAX-ACCESS      not-accessible
        STATUS          current
        DESCRIPTION
            "Table of station application category statistics"
        ::= { statistics 9 }

    stationAppCatStatsEntry OBJECT-TYPE
        SYNTAX          StationAppCatStatsEntry
        MAX-ACCESS      not-accessible
        STATUS          current
        DESCRIPTION
            "Table entry for station application category statistics"
        INDEX       { stationAppCatStatsIndex }
        ::= { stationAppCatStatsTable 1 }

    StationAppCatStatsEntry ::= SEQUENCE {
        stationAppCatStatsIndex               Integer32,
        stationAppCatStatsMACAddress          DisplayString,
        stationAppCatStatsGuid                DisplayString,
        stationAppCatStatsTxPackets           Counter64,
        stationAppCatStatsRxPackets           Counter64,
        stationAppCatStatsTxBytes             Counter64,
        stationAppCatStatsRxBytes             Counter64,
        stationAppCatStatsTimePeriod          Counter32
    }

    stationAppCatStatsIndex OBJECT-TYPE
        SYNTAX          Integer32
        MAX-ACCESS      not-accessible
        STATUS          current
        DESCRIPTION
            "Station application category statistics index"
        ::= { stationAppCatStatsEntry 1 }

    stationAppCatStatsMACAddress OBJECT-TYPE
        SYNTAX          DisplayString
        MAX-ACCESS      read-only
        STATUS          current
        DESCRIPTION
            "MAC address of the station"
        ::= { stationAppCatStatsEntry 2 }

    stationAppCatStatsGuid OBJECT-TYPE
        SYNTAX          DisplayString
        MAX-ACCESS      read-only
        STATUS          current
        DESCRIPTION
            "Global Unique ID of the application category"
        ::= { stationAppCatStatsEntry 3 }

    stationAppCatStatsTxPackets OBJECT-TYPE
        SYNTAX          Counter64
        MAX-ACCESS      read-only
        STATUS          current
        DESCRIPTION
            "Packets transmitted"
        ::= { stationAppCatStatsEntry 4 }

    stationAppCatStatsRxPackets OBJECT-TYPE
        SYNTAX          Counter64
        MAX-ACCESS      read-only
        STATUS          current
        DESCRIPTION
            "Packets received"
        ::= { stationAppCatStatsEntry 5 }

    stationAppCatStatsTxBytes OBJECT-TYPE
        SYNTAX          Counter64
        MAX-ACCESS      read-only
        STATUS          current
        DESCRIPTION
            "Bytes transmitted"
        ::= { stationAppCatStatsEntry 6 }

    stationAppCatStatsRxBytes OBJECT-TYPE
        SYNTAX          Counter64
        MAX-ACCESS      read-only
        STATUS          current
        DESCRIPTION
            "Bytes received"
        ::= { stationAppCatStatsEntry 7 }

    stationAppCatStatsTimePeriod OBJECT-TYPE
        SYNTAX          Counter32
        MAX-ACCESS      read-only
        STATUS          current
        DESCRIPTION
            "Time period over which application category stats were collected"
        ::= { stationAppCatStatsEntry 8 }

    vlanMgmtAppStatsTable OBJECT-TYPE
        SYNTAX          SEQUENCE OF VlanMgmtAppStatsEntry
        MAX-ACCESS      not-accessible
        STATUS          current
        DESCRIPTION
            "Table of VLAN management application statistics"
        ::= { statistics 10 }

    vlanMgmtAppStatsEntry OBJECT-TYPE
        SYNTAX          VlanMgmtAppStatsEntry
        MAX-ACCESS      not-accessible
        STATUS          current
        DESCRIPTION
            "Table entry for VLAN management application statistics"
        INDEX       { vlanMgmtAppStatsIndex }
        ::= { vlanMgmtAppStatsTable 1 }

    VlanMgmtAppStatsEntry ::= SEQUENCE {
        vlanMgmtAppStatsIndex               Integer32,
        vlanMgmtAppStatsVlan                Integer32,
        vlanMgmtAppStatsGuid                DisplayString,
        vlanMgmtAppStatsTxPackets           Counter64,
        vlanMgmtAppStatsRxPackets           Counter64,
        vlanMgmtAppStatsTxBytes             Counter64,
        vlanMgmtAppStatsRxBytes             Counter64,
        vlanMgmtAppStatsTimePeriod          Counter32
    }

    vlanMgmtAppStatsIndex OBJECT-TYPE
        SYNTAX          Integer32
        MAX-ACCESS      not-accessible
        STATUS          current
        DESCRIPTION
            "VLAN management application statistics index"
        ::= { vlanMgmtAppStatsEntry 1 }

    vlanMgmtAppStatsVlan OBJECT-TYPE
        SYNTAX          Integer32
        MAX-ACCESS      read-only
        STATUS          current
        DESCRIPTION
            "VLAN"
        ::= { vlanMgmtAppStatsEntry 2 }

    vlanMgmtAppStatsGuid OBJECT-TYPE
        SYNTAX          DisplayString
        MAX-ACCESS      read-only
        STATUS          current
        DESCRIPTION
            "Global Unique ID of the application"
        ::= { vlanMgmtAppStatsEntry 3 }

    vlanMgmtAppStatsTxPackets OBJECT-TYPE
        SYNTAX          Counter64
        MAX-ACCESS      read-only
        STATUS          current
        DESCRIPTION
            "Packets transmitted"
        ::= { vlanMgmtAppStatsEntry 4 }

    vlanMgmtAppStatsRxPackets OBJECT-TYPE
        SYNTAX          Counter64
        MAX-ACCESS      read-only
        STATUS          current
        DESCRIPTION
            "Packets received"
        ::= { vlanMgmtAppStatsEntry 5 }

    vlanMgmtAppStatsTxBytes OBJECT-TYPE
        SYNTAX          Counter64
        MAX-ACCESS      read-only
        STATUS          current
        DESCRIPTION
            "Bytes transmitted"
        ::= { vlanMgmtAppStatsEntry 6 }

    vlanMgmtAppStatsRxBytes OBJECT-TYPE
        SYNTAX          Counter64
        MAX-ACCESS      read-only
        STATUS          current
        DESCRIPTION
            "Bytes received"
        ::= { vlanMgmtAppStatsEntry 7 }

    vlanMgmtAppStatsTimePeriod OBJECT-TYPE
        SYNTAX          Counter32
        MAX-ACCESS      read-only
        STATUS          current
        DESCRIPTION
            "Time period over which management application stats were collected"
        ::= { vlanMgmtAppStatsEntry 8 }

    vlanMgmtAppCatStatsTable OBJECT-TYPE
        SYNTAX          SEQUENCE OF VlanMgmtAppCatStatsEntry
        MAX-ACCESS      not-accessible
        STATUS          current
        DESCRIPTION
            "Table of VLAN management application category statistics"
        ::= { statistics 11 }

    vlanMgmtAppCatStatsEntry OBJECT-TYPE
        SYNTAX          VlanMgmtAppCatStatsEntry
        MAX-ACCESS      not-accessible
        STATUS          current
        DESCRIPTION
            "Table entry for VLAN management application category statistics"
        INDEX       { vlanMgmtAppCatStatsIndex }
        ::= { vlanMgmtAppCatStatsTable 1 }

    VlanMgmtAppCatStatsEntry ::= SEQUENCE {
        vlanMgmtAppCatStatsIndex               Integer32,
        vlanMgmtAppCatStatsVlan                Integer32,
        vlanMgmtAppCatStatsGuid                DisplayString,
        vlanMgmtAppCatStatsTxPackets           Counter64,
        vlanMgmtAppCatStatsRxPackets           Counter64,
        vlanMgmtAppCatStatsTxBytes             Counter64,
        vlanMgmtAppCatStatsRxBytes             Counter64,
        vlanMgmtAppCatStatsTimePeriod          Counter32
    }

    vlanMgmtAppCatStatsIndex OBJECT-TYPE
        SYNTAX          Integer32
        MAX-ACCESS      not-accessible
        STATUS          current
        DESCRIPTION
            "VLAN management application category statistics index"
        ::= { vlanMgmtAppCatStatsEntry 1 }

    vlanMgmtAppCatStatsVlan OBJECT-TYPE
        SYNTAX          Integer32
        MAX-ACCESS      read-only
        STATUS          current
        DESCRIPTION
            "VLAN"
        ::= { vlanMgmtAppCatStatsEntry 2 }

    vlanMgmtAppCatStatsGuid OBJECT-TYPE
        SYNTAX          DisplayString
        MAX-ACCESS      read-only
        STATUS          current
        DESCRIPTION
            "Global Unique ID of the application category"
        ::= { vlanMgmtAppCatStatsEntry 3 }

    vlanMgmtAppCatStatsTxPackets OBJECT-TYPE
        SYNTAX          Counter64
        MAX-ACCESS      read-only
        STATUS          current
        DESCRIPTION
            "Packets transmitted"
        ::= { vlanMgmtAppCatStatsEntry 4 }

    vlanMgmtAppCatStatsRxPackets OBJECT-TYPE
        SYNTAX          Counter64
        MAX-ACCESS      read-only
        STATUS          current
        DESCRIPTION
            "Packets received"
        ::= { vlanMgmtAppCatStatsEntry 5 }

    vlanMgmtAppCatStatsTxBytes OBJECT-TYPE
        SYNTAX          Counter64
        MAX-ACCESS      read-only
        STATUS          current
        DESCRIPTION
            "Bytes transmitted"
        ::= { vlanMgmtAppCatStatsEntry 6 }

    vlanMgmtAppCatStatsRxBytes OBJECT-TYPE
        SYNTAX          Counter64
        MAX-ACCESS      read-only
        STATUS          current
        DESCRIPTION
            "Bytes received"
        ::= { vlanMgmtAppCatStatsEntry 7 }

    vlanMgmtAppCatStatsTimePeriod OBJECT-TYPE
        SYNTAX          Counter32
        MAX-ACCESS      read-only
        STATUS          current
        DESCRIPTION
            "Time period over which management application category stats were collected"
        ::= { vlanMgmtAppCatStatsEntry 8 }

    vlanStaAppStatsTable OBJECT-TYPE
        SYNTAX          SEQUENCE OF VlanStaAppStatsEntry
        MAX-ACCESS      not-accessible
        STATUS          current
        DESCRIPTION
            "Table of VLAN station application statistics"
        ::= { statistics 12 }

    vlanStaAppStatsEntry OBJECT-TYPE
        SYNTAX          VlanStaAppStatsEntry
        MAX-ACCESS      not-accessible
        STATUS          current
        DESCRIPTION
            "Table entry for VLAN station application statistics"
        INDEX       { vlanStaAppStatsIndex }
        ::= { vlanStaAppStatsTable 1 }

    VlanStaAppStatsEntry ::= SEQUENCE {
        vlanStaAppStatsIndex               Integer32,
        vlanStaAppStatsVlan                Integer32,
        vlanStaAppStatsGuid                DisplayString,
        vlanStaAppStatsTxPackets           Counter64,
        vlanStaAppStatsRxPackets           Counter64,
        vlanStaAppStatsTxBytes             Counter64,
        vlanStaAppStatsRxBytes             Counter64,
        vlanStaAppStatsTimePeriod          Counter32
    }

    vlanStaAppStatsIndex OBJECT-TYPE
        SYNTAX          Integer32
        MAX-ACCESS      not-accessible
        STATUS          current
        DESCRIPTION
            "VLAN station application statistics index"
        ::= { vlanStaAppStatsEntry 1 }

    vlanStaAppStatsVlan OBJECT-TYPE
        SYNTAX          Integer32
        MAX-ACCESS      read-only
        STATUS          current
        DESCRIPTION
            "VLAN"
        ::= { vlanStaAppStatsEntry 2 }

    vlanStaAppStatsGuid OBJECT-TYPE
        SYNTAX          DisplayString
        MAX-ACCESS      read-only
        STATUS          current
        DESCRIPTION
            "Global Unique ID of the application"
        ::= { vlanStaAppStatsEntry 3 }

    vlanStaAppStatsTxPackets OBJECT-TYPE
        SYNTAX          Counter64
        MAX-ACCESS      read-only
        STATUS          current
        DESCRIPTION
            "Packets transmitted"
        ::= { vlanStaAppStatsEntry 4 }

    vlanStaAppStatsRxPackets OBJECT-TYPE
        SYNTAX          Counter64
        MAX-ACCESS      read-only
        STATUS          current
        DESCRIPTION
            "Packets received"
        ::= { vlanStaAppStatsEntry 5 }

    vlanStaAppStatsTxBytes OBJECT-TYPE
        SYNTAX          Counter64
        MAX-ACCESS      read-only
        STATUS          current
        DESCRIPTION
            "Bytes transmitted"
        ::= { vlanStaAppStatsEntry 6 }

    vlanStaAppStatsRxBytes OBJECT-TYPE
        SYNTAX          Counter64
        MAX-ACCESS      read-only
        STATUS          current
        DESCRIPTION
            "Bytes received"
        ::= { vlanStaAppStatsEntry 7 }

    vlanStaAppStatsTimePeriod OBJECT-TYPE
        SYNTAX          Counter32
        MAX-ACCESS      read-only
        STATUS          current
        DESCRIPTION
            "Time period over which station application stats were collected"
        ::= { vlanStaAppStatsEntry 8 }

    vlanStaAppCatStatsTable OBJECT-TYPE
        SYNTAX          SEQUENCE OF VlanStaAppCatStatsEntry
        MAX-ACCESS      not-accessible
        STATUS          current
        DESCRIPTION
            "Table of VLAN station application category statistics"
        ::= { statistics 13 }

    vlanStaAppCatStatsEntry OBJECT-TYPE
        SYNTAX          VlanStaAppCatStatsEntry
        MAX-ACCESS      not-accessible
        STATUS          current
        DESCRIPTION
            "Table entry for VLAN station application category statistics"
        INDEX       { vlanStaAppCatStatsIndex }
        ::= { vlanStaAppCatStatsTable 1 }

    VlanStaAppCatStatsEntry ::= SEQUENCE {
        vlanStaAppCatStatsIndex               Integer32,
        vlanStaAppCatStatsVlan                Integer32,
        vlanStaAppCatStatsGuid                DisplayString,
        vlanStaAppCatStatsTxPackets           Counter64,
        vlanStaAppCatStatsRxPackets           Counter64,
        vlanStaAppCatStatsTxBytes             Counter64,
        vlanStaAppCatStatsRxBytes             Counter64,
        vlanStaAppCatStatsTimePeriod          Counter32
    }

    vlanStaAppCatStatsIndex OBJECT-TYPE
        SYNTAX          Integer32
        MAX-ACCESS      not-accessible
        STATUS          current
        DESCRIPTION
            "VLAN station application category statistics index"
        ::= { vlanStaAppCatStatsEntry 1 }

    vlanStaAppCatStatsVlan OBJECT-TYPE
        SYNTAX          Integer32
        MAX-ACCESS      read-only
        STATUS          current
        DESCRIPTION
            "VLAN"
        ::= { vlanStaAppCatStatsEntry 2 }

    vlanStaAppCatStatsGuid OBJECT-TYPE
        SYNTAX          DisplayString
        MAX-ACCESS      read-only
        STATUS          current
        DESCRIPTION
            "Global Unique ID of the application category"
        ::= { vlanStaAppCatStatsEntry 3 }

    vlanStaAppCatStatsTxPackets OBJECT-TYPE
        SYNTAX          Counter64
        MAX-ACCESS      read-only
        STATUS          current
        DESCRIPTION
            "Packets transmitted"
        ::= { vlanStaAppCatStatsEntry 4 }

    vlanStaAppCatStatsRxPackets OBJECT-TYPE
        SYNTAX          Counter64
        MAX-ACCESS      read-only
        STATUS          current
        DESCRIPTION
            "Packets received"
        ::= { vlanStaAppCatStatsEntry 5 }

    vlanStaAppCatStatsTxBytes OBJECT-TYPE
        SYNTAX          Counter64
        MAX-ACCESS      read-only
        STATUS          current
        DESCRIPTION
            "Bytes transmitted"
        ::= { vlanStaAppCatStatsEntry 6 }

    vlanStaAppCatStatsRxBytes OBJECT-TYPE
        SYNTAX          Counter64
        MAX-ACCESS      read-only
        STATUS          current
        DESCRIPTION
            "Bytes received"
        ::= { vlanStaAppCatStatsEntry 7 }

    vlanStaAppCatStatsTimePeriod OBJECT-TYPE
        SYNTAX          Counter32
        MAX-ACCESS      read-only
        STATUS          current
        DESCRIPTION
            "Time period over which station application category stats were collected"
        ::= { vlanStaAppCatStatsEntry 8 }

    stationAppStatsTablePeriod OBJECT-TYPE
        SYNTAX          Counter32(0..100000000)
        MAX-ACCESS      read-write
        STATUS          current
        DESCRIPTION
            "Specify period for station application statistics table entries (in seconds, 0 - all table entries)"
        ::= { statistics 14 }

    stationAppStatsTableClear OBJECT-TYPE
        SYNTAX          INTEGER { reset(1) }
        MAX-ACCESS      read-write
        STATUS          current
        DESCRIPTION
            "Clear the application statistics table (zero all counts)"
        ::= { statistics 15 }

    vlanStaAppStatsTablePeriod OBJECT-TYPE
        SYNTAX          Counter32(0..100000000)
        MAX-ACCESS      read-write
        STATUS          current
        DESCRIPTION
            "Specify period for VLAN station application statistics table entries (in seconds, 0 - all table entries)"
        ::= { statistics 16 }

    vlanMgmtAppStatsTablePeriod OBJECT-TYPE
        SYNTAX          Counter32(0..100000000)
        MAX-ACCESS      read-write
        STATUS          current
        DESCRIPTION
            "Specify period for management station application statistics table entries (in seconds, 0 - all table entries)"
        ::= { statistics 17 }




    staStatsTable OBJECT-TYPE
        SYNTAX          SEQUENCE OF StaStatsEntry
        MAX-ACCESS      not-accessible
        STATUS          current
        DESCRIPTION
            "Table of station statistics"
        ::= { statistics 18 }

    staStatsEntry OBJECT-TYPE
        SYNTAX          StaStatsEntry
        MAX-ACCESS      not-accessible
        STATUS          current
        DESCRIPTION
            "Table entry for station statistics"
        INDEX       { staStatsIndex }
        ::= { staStatsTable 1 }

    staStatsEntry ::= SEQUENCE {
        staStatsIndex               Integer32,
        staStatsMACAddress          DisplayString,
        staStatsRxBytes             Counter64,
        staStatsRxPackets           Counter64,
        staStatsRxErrors            Counter64,
        staStatsRxRetries           Counter64,
        staStatsTxBytes             Counter64,
        staStatsTxPackets           Counter64,
        staStatsTxErrors            Counter64,
        staStatsTxRetries           Counter64,        
        staStatsTimePeriod          Counter32
    }

    staStatsIndex OBJECT-TYPE
        SYNTAX          Integer32
        MAX-ACCESS      not-accessible
        STATUS          current
        DESCRIPTION
            "Station statistics index"
        ::= { staStatsEntry 1 }

    staStatsMACAddress OBJECT-TYPE
        SYNTAX          DisplayString
        MAX-ACCESS      read-only
        STATUS          current
        DESCRIPTION
            "MAC address of the station"
        ::= { staStatsEntry 2 }

    staStatsRxBytes OBJECT-TYPE
        SYNTAX          Counter64
        MAX-ACCESS      read-only
        STATUS          current
        DESCRIPTION
            "Bytes received"
        ::= { staStatsEntry 3 }

    staStatsRxPackets OBJECT-TYPE
        SYNTAX          Counter64
        MAX-ACCESS      read-only
        STATUS          current
        DESCRIPTION
            "Packets received"
        ::= { staStatsEntry 4 }

    staStatsRxErrors OBJECT-TYPE
        SYNTAX          Counter64
        MAX-ACCESS      read-only
        STATUS          current
        DESCRIPTION
            "Rx errors"
        ::= { staStatsEntry 5 }

    staStatsRxRetries OBJECT-TYPE
        SYNTAX          Counter64
        MAX-ACCESS      read-only
        STATUS          current
        DESCRIPTION
            "Rx retries"
        ::= { staStatsEntry 6 }


    staStatsTxBytes OBJECT-TYPE
        SYNTAX          Counter64
        MAX-ACCESS      read-only
        STATUS          current
        DESCRIPTION
            "Bytes transmitted"
        ::= { staStatsEntry 7 }

    staStatsTxPackets OBJECT-TYPE
        SYNTAX          Counter64
        MAX-ACCESS      read-only
        STATUS          current
        DESCRIPTION
            "Packets transmitted"
        ::= { staStatsEntry 8 }

    staStatsTxErrors OBJECT-TYPE
        SYNTAX          Counter64
        MAX-ACCESS      read-only
        STATUS          current
        DESCRIPTION
            "Tx errors"
        ::= { staStatsEntry 9 }

    staStatsTxRetries OBJECT-TYPE
        SYNTAX          Counter64
        MAX-ACCESS      read-only
        STATUS          current
        DESCRIPTION
            "Tx retries"
        ::= { staStatsEntry 10 }

    staStatsTimePeriod OBJECT-TYPE
        SYNTAX          Counter32
        MAX-ACCESS      read-only
        STATUS          current
        DESCRIPTION
            "Time period over which stats were collected"
        ::= { staStatsEntry 11 }



--
-- SYSLOG
--

    syslogEnable OBJECT-TYPE
        SYNTAX          INTEGER { disable(0), enable(1) }
        MAX-ACCESS      read-write
        STATUS          current
        DESCRIPTION
            "Enable or disable syslog feature"
        ::=  { syslog 1 }

    syslogLevel OBJECT-TYPE
        SYNTAX          Integer32(0..7)
        MAX-ACCESS      read-write
        STATUS          current
        DESCRIPTION
            "Local syslog level"
        ::= { syslog 2 }

    syslogServer OBJECT-TYPE
        SYNTAX          DisplayString(SIZE(0..255))
        MAX-ACCESS      read-write
        STATUS          current
        DESCRIPTION
            "Primary syslog server IP address or host name"
        ::= { syslog 3 }

    syslogConsole OBJECT-TYPE
        SYNTAX          INTEGER { disable(0), enable(1) }
        MAX-ACCESS      read-write
        STATUS          current
        DESCRIPTION
            "Enable or disable displaying log messages on the console"
        ::= { syslog 4 }

    syslogSize OBJECT-TYPE
        SYNTAX          Integer32(1..2000)
        MAX-ACCESS      read-write
        STATUS          current
        DESCRIPTION
            "Local log file size"
        ::= { syslog 5 }

    syslogTable OBJECT-TYPE
        SYNTAX          SEQUENCE OF SyslogEntry
        MAX-ACCESS      not-accessible
        STATUS          current
        DESCRIPTION
            "Event log table"
        ::= { syslog 6 }

    syslogEntry OBJECT-TYPE
        SYNTAX          SyslogEntry
        MAX-ACCESS      not-accessible
        STATUS          current
        DESCRIPTION
            "Syslog table entry"
        INDEX       { syslogIndex }
        ::= { syslogTable 1 }

    SyslogEntry ::= SEQUENCE {
        syslogIndex         Integer32,
        syslogTimestamp     DisplayString,
        syslogPriority      DisplayString,
        syslogMessage       OCTET STRING
    }

    syslogIndex OBJECT-TYPE
        SYNTAX          Integer32
        MAX-ACCESS      not-accessible
        STATUS          current
        DESCRIPTION
            "Syslog index"
        ::= { syslogEntry 1 }

    syslogTimestamp OBJECT-TYPE
        SYNTAX          DisplayString
        MAX-ACCESS      read-only
        STATUS          current
        DESCRIPTION
            "Syslog timestamp"
        ::= { syslogEntry 2 }

    syslogPriority OBJECT-TYPE
        SYNTAX          DisplayString
        MAX-ACCESS      read-only
        STATUS          current
        DESCRIPTION
            "Syslog priority"
        ::= { syslogEntry 3 }

    syslogMessage OBJECT-TYPE
        SYNTAX          OCTET STRING(SIZE(0..500))
        MAX-ACCESS      read-only
        STATUS          current
        DESCRIPTION
            "Syslog message"
        ::= { syslogEntry 4 }

    syslogSecServer OBJECT-TYPE
        SYNTAX          DisplayString(SIZE(0..255))
        MAX-ACCESS      read-write
        STATUS          current
        DESCRIPTION
            "Secondary syslog server IP address or host name"
        ::= { syslog 7 }

    syslogLevelConsole OBJECT-TYPE
        SYNTAX          Integer32(0..7)
        MAX-ACCESS      read-write
        STATUS          current
        DESCRIPTION
            "Console syslog level"
        ::= { syslog 8 }

    syslogLevelPriServer OBJECT-TYPE
        SYNTAX          Integer32(0..7)
        MAX-ACCESS      read-write
        STATUS          current
        DESCRIPTION
            "Primary server syslog level"
        ::= { syslog 9 }

    syslogLevelSecServer OBJECT-TYPE
        SYNTAX          Integer32(0..7)
        MAX-ACCESS      read-write
        STATUS          current
        DESCRIPTION
            "Secondary server syslog level"
        ::= { syslog 10 }

    syslogTerServer OBJECT-TYPE
        SYNTAX          DisplayString(SIZE(0..255))
        MAX-ACCESS      read-write
        STATUS          current
        DESCRIPTION
            "Tertiary syslog server IP address or host name"
        ::= { syslog 11 }

    syslogLevelTerServer OBJECT-TYPE
        SYNTAX          Integer32(0..7)
        MAX-ACCESS      read-write
        STATUS          current
        DESCRIPTION
            "Tertiary server syslog level"
        ::= { syslog 12 }

    syslogEmailServer OBJECT-TYPE
        SYNTAX          DisplayString(SIZE(0..255))
        MAX-ACCESS      read-write
        STATUS          current
        DESCRIPTION
            "Email syslog SMTP server IP address or host name"
        ::= { syslog 13 }

    syslogEmailLevel OBJECT-TYPE
        SYNTAX          Integer32(0..7)
        MAX-ACCESS      read-write
        STATUS          current
        DESCRIPTION
            "Email syslog level"
        ::= { syslog 14 }

    syslogEmailFromAddress OBJECT-TYPE
        SYNTAX          DisplayString(SIZE(0..255))
        MAX-ACCESS      read-write
        STATUS          current
        DESCRIPTION
            "Email Syslog from address"
        ::= { syslog 15 }

    syslogEmailToAddress OBJECT-TYPE
        SYNTAX          DisplayString(SIZE(0..255))
        MAX-ACCESS      read-write
        STATUS          current
        DESCRIPTION
            "Email Syslog recipient addresses"
        ::= { syslog 16 }

    syslogEmailUsername OBJECT-TYPE
        SYNTAX          DisplayString(SIZE(0..255))
        MAX-ACCESS      read-write
        STATUS          current
        DESCRIPTION
            "Email Syslog SMTP server username"
        ::= { syslog 17 }

    syslogEmailPassword OBJECT-TYPE
        SYNTAX          DisplayString(SIZE(0..64))
        MAX-ACCESS      read-write
        STATUS          current
        DESCRIPTION
            "Email Syslog SMTP server user password"
        ::= { syslog 18 }

    syslogEmailPasswordEnc OBJECT-TYPE
        SYNTAX          DisplayString(SIZE(0..128))
        MAX-ACCESS      read-write
        STATUS          current
        DESCRIPTION
            "Email Syslog SMTP server user password (encrypted)"
        ::= { syslog 19 }

    syslogEmailPort OBJECT-TYPE
        SYNTAX          Integer32(0..65535)
        MAX-ACCESS      read-write
        STATUS          current
        DESCRIPTION
            "Email Syslog SMTP server port"
        ::= { syslog 20 }

    syslogPriServerPort OBJECT-TYPE
        SYNTAX          Integer32(0..65535)
        MAX-ACCESS      read-write
        STATUS          current
        DESCRIPTION
            "Primary syslog server port"
        ::= { syslog 21 }

    syslogSecServerPort OBJECT-TYPE
        SYNTAX          Integer32(0..65535)
        MAX-ACCESS      read-write
        STATUS          current
        DESCRIPTION
            "Secondary syslog server port"
        ::= { syslog 22 }

    syslogTerServerPort OBJECT-TYPE
        SYNTAX          Integer32(0..65535)
        MAX-ACCESS      read-write
        STATUS          current
        DESCRIPTION
            "Tertiary syslog server port"
        ::= { syslog 23 }

    syslogStationFormat OBJECT-TYPE
        SYNTAX          INTEGER { standard(0), key-value(1) }
        MAX-ACCESS      read-write
        STATUS          current
        DESCRIPTION
            "Station information format in syslog messages"
        ::=  { syslog 24 }

    syslogTimeFormat OBJECT-TYPE
        SYNTAX          INTEGER { rfc3164(0), rfc3339(1) }
        MAX-ACCESS      read-write
        STATUS          current
        DESCRIPTION
            "Time format in syslog messages"
        ::=  { syslog 25 }

    syslogStationUrlLog OBJECT-TYPE
        SYNTAX          INTEGER { disable(0), enable(1) }
        MAX-ACCESS      read-write
        STATUS          current
        DESCRIPTION
            "Enable or disable station URL logging"
        ::= { syslog 26 }

--
-- SYSTEM
--

    systemHostname OBJECT-TYPE
        SYNTAX          DisplayString(SIZE(1.. 255))
        MAX-ACCESS      read-write
        STATUS          current
        DESCRIPTION
            "Array hostname"
        ::= { system 1 }

    systemLocation OBJECT-TYPE
        SYNTAX          DisplayString(SIZE(0..50))
        MAX-ACCESS      read-write
        STATUS          current
        DESCRIPTION
            "Array location"
        ::= { system 2 }

    systemContactName OBJECT-TYPE
        SYNTAX          DisplayString(SIZE(0..50))
        MAX-ACCESS      read-write
        STATUS          current
        DESCRIPTION
            "Contact name"
        ::= { system 3 }

    systemContactEmail OBJECT-TYPE
        SYNTAX          DisplayString(SIZE(0..50))
        MAX-ACCESS      read-write
        STATUS          current
        DESCRIPTION
            "Contact email address"
        ::= { system 4 }

    systemContactPhone OBJECT-TYPE
        SYNTAX          DisplayString(SIZE(0..50))
        MAX-ACCESS      read-write
        STATUS          current
        DESCRIPTION
            "Contact telephone number"
        ::= { system 5 }

    systemTelnetEnable OBJECT-TYPE
        SYNTAX          INTEGER { disable(0), enable(1) }
        MAX-ACCESS      read-write
        STATUS          current
        DESCRIPTION
            "Enable/disable telnet"
        ::= { system 6 }

    systemTelnetTimeout OBJECT-TYPE
        SYNTAX          Integer32(30..100000)
        MAX-ACCESS      read-write
        STATUS          current
        DESCRIPTION
            "Telnet timeout"
        ::= { system 7 }

    systemSshEnable OBJECT-TYPE
        SYNTAX          INTEGER { disable(0), enable(1) }
        MAX-ACCESS      read-write
        STATUS          current
        DESCRIPTION
            "Enable/disable ssh"
        ::= { system 8 }

    systemSshTimeout OBJECT-TYPE
        SYNTAX          Integer32(30..100000)
        MAX-ACCESS      read-write
        STATUS          current
        DESCRIPTION
            "Ssh timeout"
        ::= { system 9 }

    systemHttpsEnable OBJECT-TYPE
        SYNTAX          INTEGER { disable(0), enable(1) }
        MAX-ACCESS      read-write
        STATUS          current
        DESCRIPTION
            "Enable/disable https"
        ::= { system 10 }

    systemHttpsTimeout OBJECT-TYPE
        SYNTAX          Integer32(30..100000)
        MAX-ACCESS      read-write
        STATUS          current
        DESCRIPTION
            "Https timeout"
        ::= { system 11 }

    systemReboot OBJECT-TYPE
        SYNTAX          INTEGER { reboot(1) }
        MAX-ACCESS      read-write
        STATUS          current
        DESCRIPTION
            "Reboot array"
        ::= { system 12 }

    systemReset OBJECT-TYPE
        SYNTAX          INTEGER { reset(1) }
        MAX-ACCESS      read-write
        STATUS          current
        DESCRIPTION
            "Reset all settings to factory defaults and reboot"
        ::= { system 13 }

    systemSaveCfg OBJECT-TYPE
        SYNTAX          INTEGER { save(1) }
        MAX-ACCESS      read-write
        STATUS          current
        DESCRIPTION
            "Save running configuration to flash"
        ::= { system 14 }

    systemUptime OBJECT-TYPE
        SYNTAX          DisplayString
        MAX-ACCESS      read-only
        STATUS          current
        DESCRIPTION
            "Display time since last boot"
        ::= { system 15 }

    systemArrayInfo     OBJECT IDENTIFIER ::= { system 16 }

--
-- SYSTEM ARRAY INFO
--

    hardwareConfig      OBJECT IDENTIFIER ::= { systemArrayInfo 1 }
    softwareConfig      OBJECT IDENTIFIER ::= { systemArrayInfo 2 }

--
-- SYSTEM ARRAY INFO HARDWARE CONFIGURATION
--

    componentTable OBJECT-TYPE
        SYNTAX          SEQUENCE OF ComponentEntry
        MAX-ACCESS      not-accessible
        STATUS          current
        DESCRIPTION
            "Hardware component info table"
        ::= { hardwareConfig 1 }

    componentEntry OBJECT-TYPE
        SYNTAX          ComponentEntry
        MAX-ACCESS      not-accessible
        STATUS          current
        DESCRIPTION
            "Component table entry"
        INDEX       { componentIndex }
        ::= { componentTable 1 }

    ComponentEntry ::= SEQUENCE {
        componentIndex      Integer32,
        componentName       DisplayString,
        componentPart       DisplayString,
        componentSerial     DisplayString,
        componentDate       DisplayString
    }

    componentIndex OBJECT-TYPE
        SYNTAX          Integer32
        MAX-ACCESS      not-accessible
        STATUS          current
        DESCRIPTION
            "Component table index"
        ::= { componentEntry 1 }

    componentName OBJECT-TYPE
        SYNTAX          DisplayString
        MAX-ACCESS      read-only
        STATUS          current
        DESCRIPTION
            "Component name"
        ::= { componentEntry 2 }

    componentPart OBJECT-TYPE
        SYNTAX          DisplayString
        MAX-ACCESS      read-only
        STATUS          current
        DESCRIPTION
            "Component part number"
        ::= { componentEntry 3 }

    componentSerial OBJECT-TYPE
        SYNTAX          DisplayString
        MAX-ACCESS      read-only
        STATUS          current
        DESCRIPTION
            "Component serial number"
        ::= { componentEntry 4 }

    componentDate OBJECT-TYPE
        SYNTAX          DisplayString
        MAX-ACCESS      read-only
        STATUS          current
        DESCRIPTION
            "Component date"
        ::= { componentEntry 5 }

    fpgaTable OBJECT-TYPE
        SYNTAX          SEQUENCE OF FpgaEntry
        MAX-ACCESS      not-accessible
        STATUS          current
        DESCRIPTION
            "FPGA info table"
        ::= { hardwareConfig 2 }

    fpgaEntry OBJECT-TYPE
        SYNTAX          FpgaEntry
        MAX-ACCESS      not-accessible
        STATUS          current
        DESCRIPTION
            "FPGA table entry"
        INDEX       { fpgaIndex }
        ::= { fpgaTable 1 }

    FpgaEntry ::= SEQUENCE {
        fpgaIndex           Integer32,
        fpgaName            DisplayString,
        fpgaBootVersion     DisplayString,
        fpgaSWVersion       DisplayString
    }

    fpgaIndex OBJECT-TYPE
        SYNTAX          Integer32
        MAX-ACCESS      not-accessible
        STATUS          current
        DESCRIPTION
            "FPGA table index"
        ::= { fpgaEntry 1 }

    fpgaName OBJECT-TYPE
        SYNTAX          DisplayString
        MAX-ACCESS      read-only
        STATUS          current
        DESCRIPTION
            "FPGA name"
        ::= { fpgaEntry 2 }

    fpgaBootVersion OBJECT-TYPE
        SYNTAX          DisplayString
        MAX-ACCESS      read-only
        STATUS          current
        DESCRIPTION
            "FPGA boot version"
        ::= { fpgaEntry 3 }

    fpgaSWVersion OBJECT-TYPE
        SYNTAX          DisplayString
        MAX-ACCESS      read-only
        STATUS          current
        DESCRIPTION
            "FPGA software version"
        ::= { fpgaEntry 4 }

    interfaceMACAddressTable OBJECT-TYPE
        SYNTAX          SEQUENCE OF InterfaceMACAddressEntry
        MAX-ACCESS      not-accessible
        STATUS          current
        DESCRIPTION
            "Interface MAC address table"
        ::= { hardwareConfig 3 }

    interfaceMACAddressEntry OBJECT-TYPE
        SYNTAX          InterfaceMACAddressEntry
        MAX-ACCESS      not-accessible
        STATUS          current
        DESCRIPTION
            "Interface MAC address table entry"
        INDEX       { interfaceMACAddressIndex }
        ::= { interfaceMACAddressTable 1 }

    InterfaceMACAddressEntry ::= SEQUENCE {
        interfaceMACAddressIndex    Integer32,
        interfaceName               DisplayString,
        interfaceMACAddress         DisplayString
    }

    interfaceMACAddressIndex OBJECT-TYPE
        SYNTAX          Integer32
        MAX-ACCESS      not-accessible
        STATUS          current
        DESCRIPTION
            "Interface MAC address table index"
        ::= { interfaceMACAddressEntry 1 }

    interfaceName OBJECT-TYPE
        SYNTAX          DisplayString
        MAX-ACCESS      read-only
        STATUS          current
        DESCRIPTION
            "Interface name"
        ::= { interfaceMACAddressEntry 2 }

    interfaceMACAddress OBJECT-TYPE
        SYNTAX          DisplayString
        MAX-ACCESS      read-only
        STATUS          current
        DESCRIPTION
            "Interface MAC address"
        ::= { interfaceMACAddressEntry 3 }

    arrayModel OBJECT-TYPE
        SYNTAX          DisplayString
        MAX-ACCESS      read-only
        STATUS          current
        DESCRIPTION
            "Array model"
        ::= { hardwareConfig 4 }

--
-- SYSTEM ARRAY INFO SOFTWARE CONFIGURATION
--

    bootLoaderVersion OBJECT-TYPE
        SYNTAX          DisplayString
        MAX-ACCESS      read-only
        STATUS          current
        DESCRIPTION
            "Boot loader version"
        ::= { softwareConfig 1 }

    iapDriverVersion OBJECT-TYPE
        SYNTAX          DisplayString
        MAX-ACCESS      read-only
        STATUS          current
        DESCRIPTION
            "IAP driver version"
        ::= { softwareConfig 2 }

    softwareVersion OBJECT-TYPE
        SYNTAX          DisplayString
        MAX-ACCESS      read-only
        STATUS          current
        DESCRIPTION
            "Software version"
        ::= { softwareConfig 3 }

    timeThisBoot OBJECT-TYPE
        SYNTAX          DisplayString
        MAX-ACCESS      read-only
        STATUS          current
        DESCRIPTION
            "Time of this boot"
        ::= { softwareConfig 4 }

    timeLastBoot OBJECT-TYPE
        SYNTAX          DisplayString
        MAX-ACCESS      read-only
        STATUS          current
        DESCRIPTION
            "Time of the last boot"
        ::= { softwareConfig 5 }

    scdFirmwareVersion OBJECT-TYPE
        SYNTAX          DisplayString
        MAX-ACCESS      read-only
        STATUS          current
        DESCRIPTION
            "SCD firmware version"
        ::= { softwareConfig 6 }

    systemMIBVersion OBJECT-TYPE
        SYNTAX          DisplayString
        MAX-ACCESS      read-only
        STATUS          current
        DESCRIPTION
            "MIB version"
        ::= { system 17 }

    systemGroupName OBJECT-TYPE
        SYNTAX          DisplayString(SIZE(0..50))
        MAX-ACCESS      read-write
        STATUS          current
        DESCRIPTION
            "Array group name"
        ::= { system 18 }

    systemStandbyEnable OBJECT-TYPE
        SYNTAX          INTEGER { disable(0), enable(1) }
        MAX-ACCESS      read-write
        STATUS          current
        DESCRIPTION
            "Enable/disable standby"
        ::= { system 19 }

    systemStandbyTarget OBJECT-TYPE
        SYNTAX          DisplayString(SIZE(17..17))
        MAX-ACCESS      read-write
        STATUS          current
        DESCRIPTION
            "Target array to monitor for failure"
        ::= { system 20 }

    systemTempTable OBJECT-TYPE
        SYNTAX          SEQUENCE OF SystemTempEntry
        MAX-ACCESS      not-accessible
        STATUS          current
        DESCRIPTION
            "System temperature table"
        ::= { system 21 }

    systemTempEntry OBJECT-TYPE
        SYNTAX          SystemTempEntry
        MAX-ACCESS      not-accessible
        STATUS          current
        DESCRIPTION
            "System temperature table entry"
        INDEX       { systemTempIndex }
        ::= { systemTempTable 1 }

    SystemTempEntry ::= SEQUENCE {
        systemTempIndex         Integer32,
        systemTempComponent     DisplayString,
        systemTempCelsius       Integer32,
        systemTempFahrenheit    Integer32
    }

    systemTempIndex OBJECT-TYPE
        SYNTAX          Integer32
        MAX-ACCESS      not-accessible
        STATUS          current
        DESCRIPTION
            "System temperature table index"
        ::= { systemTempEntry 1 }

    systemTempComponent OBJECT-TYPE
        SYNTAX          DisplayString
        MAX-ACCESS      read-only
        STATUS          current
        DESCRIPTION
            "System component name"
        ::= { systemTempEntry 2 }

    systemTempCelsius OBJECT-TYPE
        SYNTAX          Integer32
        MAX-ACCESS      read-only
        STATUS          current
        DESCRIPTION
            "System component temperature (Celsius)"
        ::= { systemTempEntry 3 }

    systemTempFahrenheit OBJECT-TYPE
        SYNTAX          Integer32
        MAX-ACCESS      read-only
        STATUS          current
        DESCRIPTION
            "System component temperature (Fahrenheit)"
        ::= { systemTempEntry 4 }

    systemFipsMode OBJECT-TYPE
        SYNTAX          INTEGER { disable(0), enable(1) }
        MAX-ACCESS      read-write
        STATUS          current
        DESCRIPTION
            "Enable/disable FIPS mode"
        ::= { system 22 }

    systemTelnetPort OBJECT-TYPE
        SYNTAX          Integer32(0..65535)
        MAX-ACCESS      read-write
        STATUS          current
        DESCRIPTION
            "Telnet port"
        ::= { system 23 }

    systemSshPort OBJECT-TYPE
        SYNTAX          Integer32(0..65535)
        MAX-ACCESS      read-write
        STATUS          current
        DESCRIPTION
            "Ssh port"
        ::= { system 24 }

    systemHttpsPort OBJECT-TYPE
        SYNTAX          Integer32(0..65535)
        MAX-ACCESS      read-write
        STATUS          current
        DESCRIPTION
            "Https port"
        ::= { system 25 }

    systemLicenseKey OBJECT-TYPE
        SYNTAX          DisplayString(SIZE(23..23))
        MAX-ACCESS      read-write
        STATUS          current
        DESCRIPTION
            "Set array software license key"
        ::= { system 26 }

    systemLicenseFeatures OBJECT-TYPE
        SYNTAX          DisplayString
        MAX-ACCESS      read-only
        STATUS          current
        DESCRIPTION
            "Software license features"
        ::= { system 27 }

    systemRemoteServer OBJECT-TYPE
        SYNTAX          IpAddress
        MAX-ACCESS      read-write
        STATUS          current
        DESCRIPTION
            "Specify TFTP server for remote software image"
        ::= { system 28 }

    systemRemoteImage OBJECT-TYPE
        SYNTAX          DisplayString(SIZE(0.. 255))
        MAX-ACCESS      read-write
        STATUS          current
        DESCRIPTION
            "Specify a remote array software image"
        ::= { system 29 }

    systemRemoteConfigFile OBJECT-TYPE
        SYNTAX          DisplayString(SIZE(0.. 255))
        MAX-ACCESS      read-write
        STATUS          current
        DESCRIPTION
            "Specify a remote array configuration file"
        ::= { system 30 }

    systemHttpsCertificate OBJECT-TYPE
        SYNTAX          INTEGER { reset(0), self(1), xirrus(2), new(3) }
        MAX-ACCESS      read-write
        STATUS          current
        DESCRIPTION
            "Set HTTPS certificate"
        ::= { system 31 }

    systemPCIAuditMode OBJECT-TYPE
        SYNTAX          INTEGER { disable(0), enable(1) }
        MAX-ACCESS      read-write
        STATUS          current
        DESCRIPTION
            "Enable/disable PCI (Payment Card Industry) audit mode"
        ::= { system 32 }

    systemNetworkAssurance OBJECT-TYPE
        SYNTAX          INTEGER { disable(0), enable(1) }
        MAX-ACCESS      read-write
        STATUS          current
        DESCRIPTION
            "Enable/disable network assurance"
        ::= { system 33 }

    systemLicenseVersion OBJECT-TYPE
        SYNTAX          DisplayString
        MAX-ACCESS      read-only
        STATUS          current
        DESCRIPTION
            "Software license version"
        ::= { system 34 }

    systemLicenseExpDate OBJECT-TYPE
        SYNTAX          DisplayString
        MAX-ACCESS      read-only
        STATUS          current
        DESCRIPTION
            "Software license expiration date"
        ::= { system 35 }

    licenseFeatureTable OBJECT-TYPE
        SYNTAX          SEQUENCE OF LicenseFeatureEntry
        MAX-ACCESS      not-accessible
        STATUS          current
        DESCRIPTION
            "Software license feature list"
        ::= { system 36}

    licenseFeatureEntry OBJECT-TYPE
        SYNTAX          LicenseFeatureEntry
        MAX-ACCESS      not-accessible
        STATUS          current
        DESCRIPTION
            "Software license feature table entry"
        INDEX       {  licenseFeatureIndex }
        ::= {  licenseFeatureTable 1 }

    LicenseFeatureEntry ::= SEQUENCE {
        licenseFeatureIndex         Integer32,
        licenseFeatureName          DisplayString,
        licenseFeatureStatus        INTEGER,
        licenseFeatureDesc          DisplayString
    }

    licenseFeatureIndex OBJECT-TYPE
        SYNTAX          Integer32
        MAX-ACCESS      not-accessible
        STATUS          current
        DESCRIPTION
            "License feature table index"
        ::= { licenseFeatureEntry 1 }

    licenseFeatureName OBJECT-TYPE
        SYNTAX          DisplayString
        MAX-ACCESS      read-only
        STATUS          current
        DESCRIPTION
            "License feature name"
        ::= { licenseFeatureEntry 2 }

    licenseFeatureStatus OBJECT-TYPE
        SYNTAX          INTEGER { disabled(0), enabled(1) }
        MAX-ACCESS      read-only
        STATUS          current
        DESCRIPTION
            "License feature status"
        ::= { licenseFeatureEntry 3 }

    licenseFeatureDesc OBJECT-TYPE
        SYNTAX          DisplayString
        MAX-ACCESS      read-only
        STATUS          current
        DESCRIPTION
           "License feature description"
        ::= { licenseFeatureEntry 4 }

    systemRDKMode OBJECT-TYPE
        SYNTAX          INTEGER { disabled(0), enabled(1) }
        MAX-ACCESS      read-only
        STATUS          current
        DESCRIPTION
            "Rapid Deployment Kit mode"
        ::= { system 37 }

    systemMaxAuthAttempts OBJECT-TYPE
        SYNTAX          Integer32(0..255)
        MAX-ACCESS      read-write
        STATUS          current
        DESCRIPTION
            "Maximum number of authentication (login) attempts (0 means unlimited)"
        ::= { system 38 }

    systemLoginReauthPeriod OBJECT-TYPE
        SYNTAX          Integer32(0..65535)
        MAX-ACCESS      read-write
        STATUS          current
        DESCRIPTION
            "Time between failed CLI login attempts"
        ::= { system 39 }

    systemPreLoginBanner OBJECT-TYPE
        SYNTAX          OCTET STRING(SIZE(0..1000))
        MAX-ACCESS      read-write
        STATUS          current
        DESCRIPTION
            "Set pre-login banner message"
        ::= { system 40 }

    systemPostLoginBanner OBJECT-TYPE
        SYNTAX          OCTET STRING(SIZE(0..1000))
        MAX-ACCESS      read-write
        STATUS          current
        DESCRIPTION
            "Set post-login banner message"
        ::= { system 41 }

    systemResetReason OBJECT-TYPE
        SYNTAX          DisplayString
        MAX-ACCESS      read-only
        STATUS          current
        DESCRIPTION
            "Reason for last reboot"
        ::= { system 42 }

    systemResetCode OBJECT-TYPE
        SYNTAX          INTEGER { reboot-req(0), power-on(1), power-brown-out(2),
                                  scd-restart(3), gpc(4), unavailable(5) }
        MAX-ACCESS      read-only
        STATUS          current
        DESCRIPTION
            "Code for last reboot"
        ::= { system 43 }

    systemNetworkAssurancePeriod OBJECT-TYPE
        SYNTAX          Integer32(60..900)
        MAX-ACCESS      read-write
        STATUS          current
        DESCRIPTION
            "Set network assurance period (in seconds)"
        ::= { system 44 }

    systemLicenseProductType OBJECT-TYPE
        SYNTAX          INTEGER { unknown(0), array2x3(1), array2x2(2), array3x3(3) }
        MAX-ACCESS      read-only
        STATUS          current
        DESCRIPTION
            "Software license product type"
        ::= { system 45 }

    systemLicenseMaxNumIAPs OBJECT-TYPE
        SYNTAX          Integer32
        MAX-ACCESS      read-only
        STATUS          current
        DESCRIPTION
            "Software license maximum number of IAPs"
        ::= { system 46 }

    systemCrashInfo OBJECT-TYPE
        SYNTAX          OCTET STRING(SIZE(0..4096))
        MAX-ACCESS      read-only
        STATUS          current
        DESCRIPTION
            "System crash information"
        ::= { system 47 }

    systemCompassHeading OBJECT-TYPE
        SYNTAX          Integer32
        MAX-ACCESS      read-only
        STATUS          current
        DESCRIPTION
            "System compass heading (in degrees, -1 - unknown)"
        ::= { system 48 }

    systemXirconEnable OBJECT-TYPE
        SYNTAX          INTEGER { disable(0), enable-aos-only(1),
                                  enable-boot-only(2),  enable-aos-boot(3) }
        MAX-ACCESS      read-write
        STATUS          current
        DESCRIPTION
            "Enable/disable xircon access"
        ::= { system 49 }

    systemXirconTimeout OBJECT-TYPE
        SYNTAX          Integer32(30..100000)
        MAX-ACCESS      read-write
        STATUS          current
        DESCRIPTION
            "Xircon inactivity timeout"
        ::= { system 50 }

    systemXirconPort OBJECT-TYPE
        SYNTAX          Integer32(1025..65535)
        MAX-ACCESS      read-write
        STATUS          current
        DESCRIPTION
            "Xircon port"
        ::= { system 51 }

    systemStpEnable OBJECT-TYPE
        SYNTAX          INTEGER { disable(0), enable(1) }
        MAX-ACCESS      read-write
        STATUS          current
        DESCRIPTION
            "Enable/disable Spanning Tree Protocol"
        ::= { system 52 }

    systemFanSpeed OBJECT-TYPE
        SYNTAX          Integer32
        MAX-ACCESS      read-only
        STATUS          current
        DESCRIPTION
            "System fan speed (RPM)"
        ::= { system 53 }

    systemXmsControl OBJECT-TYPE
        SYNTAX          INTEGER { off(0), on(1) }
        MAX-ACCESS      read-write
        STATUS          current
        DESCRIPTION
            "Allow all user management or restrict to console and XMS only"
        ::= { system 54 }

    systemActivation OBJECT-TYPE
        SYNTAX          INTEGER { disable(0), enable(1) }
        MAX-ACCESS      read-write
        STATUS          current
        DESCRIPTION
            "Enable/disable array activation"
        ::= { system 55 }

    systemActivationInterval OBJECT-TYPE
        SYNTAX          Integer32(1..1000000)
        MAX-ACCESS      read-write
        STATUS          current
        DESCRIPTION
            "Array activation polling interval (minutes)"
        ::= { system 56 }

    systemStatusLed OBJECT-TYPE
        SYNTAX          INTEGER { disable(0), enable(1) }
        MAX-ACCESS      read-write
        STATUS          current
        DESCRIPTION
            "Enable/disable Status LED"
        ::= { system 57 }

    systemResetButton OBJECT-TYPE
        SYNTAX          INTEGER { disable(0), enable(1) }
        MAX-ACCESS      read-write
        STATUS          current
        DESCRIPTION
            "Enable/disable Reset Button"
        ::= { system 58 }

--
-- TUNNEL
--

    tunnelTable OBJECT-TYPE
        SYNTAX          SEQUENCE OF TunnelEntry
        MAX-ACCESS      not-accessible
        STATUS          current
        DESCRIPTION
            "Tunnel table"
        ::= { tunnel 1 }

    tunnelEntry OBJECT-TYPE
        SYNTAX          TunnelEntry
        MAX-ACCESS      not-accessible
        STATUS          current
        DESCRIPTION
            "Tunnel table entry"
        INDEX       { tunnelIndex }
        ::= { tunnelTable 1 }

    TunnelEntry ::= SEQUENCE {
        tunnelIndex                 Integer32,
        tunnelName                  DisplayString,
        tunnelEnable                INTEGER,
        tunnelType                  INTEGER,
        tunnelLocalEndpoint         IpAddress,
        tunnelPriRemoteEndpoint     IpAddress,
        tunnelSecRemoteEndpoint     IpAddress,
        tunnelMTU                   Integer32,
        tunnelSsids                 Integer32,
        tunnelDhcpOption            INTEGER,
        tunnelFailoverInterval      Integer32,
        tunnelFailoverNumFailures   Integer32,
        tunnelRowStatus             RowStatus,
        tunnelVlanList              OCTET STRING
    }

    tunnelIndex OBJECT-TYPE
        SYNTAX          Integer32
        MAX-ACCESS      not-accessible
        STATUS          current
        DESCRIPTION
            "Tunnel table index"
        ::= { tunnelEntry 1 }

    tunnelName OBJECT-TYPE
        SYNTAX          DisplayString(SIZE(1..20))
        MAX-ACCESS      read-create
        STATUS          current
        DESCRIPTION
            "Tunnel name"
        ::= { tunnelEntry 2 }

    tunnelEnable OBJECT-TYPE
        SYNTAX          INTEGER { disable(0), enable(1) }
        MAX-ACCESS      read-create
        STATUS          current
        DESCRIPTION
            "Enable or disable tunnel"
        ::= { tunnelEntry 3 }

    tunnelType OBJECT-TYPE
        SYNTAX          INTEGER { none(0), gre(1) }
        MAX-ACCESS      read-create
        STATUS          current
        DESCRIPTION
            "Tunnel type"
        ::= { tunnelEntry 4 }

    tunnelLocalEndpoint OBJECT-TYPE
        SYNTAX          IpAddress
        MAX-ACCESS      read-create
        STATUS          current
        DESCRIPTION
            "Tunnel local endpoint"
        ::= { tunnelEntry 5 }

    tunnelPriRemoteEndpoint OBJECT-TYPE
        SYNTAX          IpAddress
        MAX-ACCESS      read-create
        STATUS          current
        DESCRIPTION
            "Tunnel primary remote endpoint"
        ::= { tunnelEntry 6 }

    tunnelSecRemoteEndpoint OBJECT-TYPE
        SYNTAX          IpAddress
        MAX-ACCESS      read-create
        STATUS          current
        DESCRIPTION
            "Tunnel secondary remote endpoint"
        ::= { tunnelEntry 7 }

    tunnelMTU OBJECT-TYPE
        SYNTAX          Integer32(68..1732)
        MAX-ACCESS      read-create
        STATUS          current
        DESCRIPTION
            "Tunnel MTU"
        ::= { tunnelEntry 8 }

    tunnelSsids OBJECT-TYPE
        SYNTAX          Integer32(0..65535)
        MAX-ACCESS      read-create
        STATUS          current
        DESCRIPTION
            "Define SSIDs for which data traffic should be bridged via this tunnel"
        ::= { tunnelEntry 9 }

    tunnelDhcpOption OBJECT-TYPE
        SYNTAX          INTEGER { disable(0), enable(1) }
        MAX-ACCESS      read-create
        STATUS          current
        DESCRIPTION
            "Enable or disable insertion of relay agent information option in station DHCP requests"
        ::= { tunnelEntry 10 }

    tunnelFailoverInterval OBJECT-TYPE
        SYNTAX          Integer32(5..3600)
        MAX-ACCESS      read-create
        STATUS          current
        DESCRIPTION
            "Ping interval for remote endpoint failover mechanism"
        ::= { tunnelEntry 11 }

    tunnelFailoverNumFailures OBJECT-TYPE
        SYNTAX          Integer32(3..1000)
        MAX-ACCESS      read-create
        STATUS          current
        DESCRIPTION
            "Number of ping failures for remote endpoint failover mechanism"
        ::= { tunnelEntry 12 }

    tunnelRowStatus OBJECT-TYPE
        SYNTAX          RowStatus
        MAX-ACCESS      read-create
        STATUS          current
        DESCRIPTION
            "Status of the tunnel row entry"
        ::= { tunnelEntry 13 }

    tunnelVlanList OBJECT-TYPE
        SYNTAX          OCTET STRING(SIZE(0..320))
        MAX-ACCESS      read-create
        STATUS          current
        DESCRIPTION
            "Define VLANs for which data traffic should be bridged via this tunnel"
        ::= { tunnelEntry 14 }

    tunnelTableReset OBJECT-TYPE
        SYNTAX          INTEGER { reset(1) }
        MAX-ACCESS      read-write
        STATUS          current
        DESCRIPTION
            "Delete all tunnels"
        ::= { tunnel 2 }

--
-- VLAN
--

    vlanTableReset OBJECT-TYPE
        SYNTAX          INTEGER { reset(1) }
        MAX-ACCESS      read-write
        STATUS          current
        DESCRIPTION
            "Reset VLAN table (clear all entries)"
        ::= { vlan 1 }

    vlanTable OBJECT-TYPE
        SYNTAX          SEQUENCE OF VlanEntry
        MAX-ACCESS      not-accessible
        STATUS          current
        DESCRIPTION
            "VLAN table for the Array"
        ::= { vlan 2 }

    vlanEntry OBJECT-TYPE
        SYNTAX          VlanEntry
        MAX-ACCESS      not-accessible
        STATUS          current
        DESCRIPTION
            "VLAN table entry"
        INDEX       { vlanIndex }
        ::= { vlanTable 1 }

    VlanEntry ::= SEQUENCE {
        vlanIndex               Integer32,
        vlanName                DisplayString,
        vlanNumber              Integer32,
        vlanMgmt                INTEGER,
        vlanDHCPBind            INTEGER,
        vlanIPAddress           IpAddress,
        vlanIPMask              IpAddress,
        vlanGateway             IpAddress,
        vlanRowStatus           RowStatus,
        vlanTunnelServer        DisplayString,
        vlanTunnelSecret        DisplayString,
        vlanTunnelPort          Integer32,
        vlanTunnelState         INTEGER,
        vlanTunnelSecretForm    INTEGER,
        vlanFastRoaming         INTEGER
    }

    vlanIndex OBJECT-TYPE
        SYNTAX          Integer32
        MAX-ACCESS      not-accessible
        STATUS          current
        DESCRIPTION
            "VLAN table index"
        ::= { vlanEntry 1 }

    vlanName OBJECT-TYPE
        SYNTAX          DisplayString(SIZE(1..20))
        MAX-ACCESS      read-create
        STATUS          current
        DESCRIPTION
            "VLAN name"
        ::= { vlanEntry 2 }

    vlanNumber OBJECT-TYPE
        SYNTAX          Integer32(1..4095)
        MAX-ACCESS      read-create
        STATUS          current
        DESCRIPTION
            "VLAN number"
        ::= { vlanEntry 3 }

    vlanMgmt OBJECT-TYPE
        SYNTAX          INTEGER { disable(0), enable(1) }
        MAX-ACCESS      read-create
        STATUS          current
        DESCRIPTION
            "Enable/disable management via VLAN"
        ::= { vlanEntry 4 }

    vlanDHCPBind OBJECT-TYPE
        SYNTAX          INTEGER { disable(0), enable(1) }
        MAX-ACCESS      read-create
        STATUS          current
        DESCRIPTION
            "Use DHCP to get IP settings for VLAN"
        ::= { vlanEntry 5 }

    vlanIPAddress OBJECT-TYPE
        SYNTAX          IpAddress
        MAX-ACCESS      read-create
        STATUS          current
        DESCRIPTION
            "VLAN IP address"
        ::= { vlanEntry 6 }

    vlanIPMask OBJECT-TYPE
        SYNTAX          IpAddress
        MAX-ACCESS      read-create
        STATUS          current
        DESCRIPTION
            "VLAN IP Mask"
        ::= { vlanEntry 7 }

    vlanGateway OBJECT-TYPE
        SYNTAX          IpAddress
        MAX-ACCESS      read-create
        STATUS          current
        DESCRIPTION
            "VLAN gateway IP address"
        ::= { vlanEntry 8 }

    vlanRowStatus OBJECT-TYPE
        SYNTAX          RowStatus
        MAX-ACCESS      read-create
        STATUS          current
        DESCRIPTION
            "Status of the VLAN row entry"
        ::= { vlanEntry 9 }

    vlanTunnelServer OBJECT-TYPE
        SYNTAX          DisplayString(SIZE(0.. 255))
        MAX-ACCESS      read-create
        STATUS          current
        DESCRIPTION
            "VLAN tunnel server IP address or host name"
        ::= { vlanEntry 10 }

    vlanTunnelSecret OBJECT-TYPE
        SYNTAX          DisplayString(SIZE(0..128))
        MAX-ACCESS      read-create
        STATUS          current
        DESCRIPTION
            "VLAN tunnel server password"
        ::= { vlanEntry 11 }

    vlanTunnelPort OBJECT-TYPE
        SYNTAX          Integer32(0..65535)
        MAX-ACCESS      read-create
        STATUS          current
        DESCRIPTION
            "VLAN tunnel server port number"
        ::= { vlanEntry 12 }

    vlanTunnelState OBJECT-TYPE
        SYNTAX          INTEGER { not-connected(0), connected(1) }
        MAX-ACCESS      read-only
        STATUS          current
        DESCRIPTION
            "VLAN tunnel state"
        ::= { vlanEntry 13 }

    vlanTunnelSecretForm OBJECT-TYPE
        SYNTAX          INTEGER { clear(0), encrypted(1) }
        MAX-ACCESS      read-create
        STATUS          current
        DESCRIPTION
            "VLAN tunnel server password form"
        ::= { vlanEntry 14 }

    vlanFastRoaming OBJECT-TYPE
        SYNTAX          INTEGER { disable(0), enable(1) }
        MAX-ACCESS      read-create
        STATUS          current
        DESCRIPTION
            "Enable/disable fast roaming (at layer 3) for VLAN"
        ::= { vlanEntry 15 }

    spanningTreeTable OBJECT-TYPE
        SYNTAX          SEQUENCE OF SpanningTreeEntry
        MAX-ACCESS      not-accessible
        STATUS          current
        DESCRIPTION
            "Spanning tree state table"
        ::= { vlan 3 }

    spanningTreeEntry OBJECT-TYPE
        SYNTAX          SpanningTreeEntry
        MAX-ACCESS      not-accessible
        STATUS          current
        DESCRIPTION
            "Spanning tree table entry"
        INDEX       { spanningTreeIndex }
        ::= { spanningTreeTable 1 }

    SpanningTreeEntry ::= SEQUENCE {
        spanningTreeIndex                   Integer32,
        spanningTreeVlanName                DisplayString,
        spanningTreeVlanNumber              Integer32,
        spanningTreeGigLinkState            DisplayString,
        spanningTreeWDSClientLink1State     DisplayString,
        spanningTreeWDSClientLink2State     DisplayString,
        spanningTreeWDSClientLink3State     DisplayString,
        spanningTreeWDSClientLink4State     DisplayString,
        spanningTreeWDSHostLink1State       DisplayString,
        spanningTreeWDSHostLink2State       DisplayString,
        spanningTreeWDSHostLink3State       DisplayString,
        spanningTreeWDSHostLink4State       DisplayString
    }

    spanningTreeIndex OBJECT-TYPE
        SYNTAX          Integer32
        MAX-ACCESS      not-accessible
        STATUS          current
        DESCRIPTION
            "Spanning tree table index"
        ::= { spanningTreeEntry 1 }

    spanningTreeVlanName OBJECT-TYPE
        SYNTAX          DisplayString
        MAX-ACCESS      read-only
        STATUS          current
        DESCRIPTION
            "VLAN name"
        ::= { spanningTreeEntry 2 }

    spanningTreeVlanNumber OBJECT-TYPE
        SYNTAX          Integer32
        MAX-ACCESS      read-only
        STATUS          current
        DESCRIPTION
            "VLAN number"
        ::= { spanningTreeEntry 3 }

    spanningTreeGigLinkState OBJECT-TYPE
        SYNTAX          DisplayString
        MAX-ACCESS      read-only
        STATUS          current
        DESCRIPTION
            "Gigabit link state"
        ::= { spanningTreeEntry 4 }

    spanningTreeWDSClientLink1State OBJECT-TYPE
        SYNTAX          DisplayString
        MAX-ACCESS      read-only
        STATUS          current
        DESCRIPTION
            "WDS client link 1 state"
        ::= { spanningTreeEntry 5 }

    spanningTreeWDSClientLink2State OBJECT-TYPE
        SYNTAX          DisplayString
        MAX-ACCESS      read-only
        STATUS          current
        DESCRIPTION
            "WDS client link 2 state"
        ::= { spanningTreeEntry 6 }

    spanningTreeWDSClientLink3State OBJECT-TYPE
        SYNTAX          DisplayString
        MAX-ACCESS      read-only
        STATUS          current
        DESCRIPTION
            "WDS client link 3 state"
        ::= { spanningTreeEntry 7 }

    spanningTreeWDSClientLink4State OBJECT-TYPE
        SYNTAX          DisplayString
        MAX-ACCESS      read-only
        STATUS          current
        DESCRIPTION
            "WDS client link 4 state"
        ::= { spanningTreeEntry 8 }

    spanningTreeWDSHostLink1State OBJECT-TYPE
        SYNTAX          DisplayString
        MAX-ACCESS      read-only
        STATUS          current
        DESCRIPTION
            "WDS host link 1 state"
        ::= { spanningTreeEntry 9 }

    spanningTreeWDSHostLink2State OBJECT-TYPE
        SYNTAX          DisplayString
        MAX-ACCESS      read-only
        STATUS          current
        DESCRIPTION
            "WDS host link 2 state"
        ::= { spanningTreeEntry 10 }

    spanningTreeWDSHostLink3State OBJECT-TYPE
        SYNTAX          DisplayString
        MAX-ACCESS      read-only
        STATUS          current
        DESCRIPTION
            "WDS host link 3 state"
        ::= { spanningTreeEntry 11 }

    spanningTreeWDSHostLink4State OBJECT-TYPE
        SYNTAX          DisplayString
        MAX-ACCESS      read-only
        STATUS          current
        DESCRIPTION
            "WDS host link 4 state"
        ::= { spanningTreeEntry 12 }

    vlanDefaultNumber OBJECT-TYPE
        SYNTAX          Integer32(0..4095)
        MAX-ACCESS      read-write
        STATUS          current
        DESCRIPTION
            "VLAN number(1-4095) to assign as default, 0 - no VLAN as default"
        ::= { vlan 4 }

    vlanNativeNumber OBJECT-TYPE
        SYNTAX          Integer32(0..4095)
        MAX-ACCESS      read-write
        STATUS          current
        DESCRIPTION
            "VLAN number(1-4095) to assign as native, 0 - no VLAN as native"
        ::= { vlan 5 }

    vlanUndefinedTable OBJECT-TYPE
        SYNTAX          SEQUENCE OF VlanUndefinedEntry
        MAX-ACCESS      not-accessible
        STATUS          current
        DESCRIPTION
            "Table of undefined VLANs detected"
        ::= { vlan 6 }

    vlanUndefinedEntry OBJECT-TYPE
        SYNTAX          VlanUndefinedEntry
        MAX-ACCESS      not-accessible
        STATUS          current
        DESCRIPTION
            "Undefined VLAN table entry"
        INDEX       { vlanUndefinedIndex }
        ::= { vlanUndefinedTable 1 }

    VlanUndefinedEntry ::= SEQUENCE {
        vlanUndefinedIndex          Integer32,
        vlanUndefinedNumber         Integer32
    }

    vlanUndefinedIndex OBJECT-TYPE
        SYNTAX          Integer32
        MAX-ACCESS      not-accessible
        STATUS          current
        DESCRIPTION
            "Undefined VLAN table index"
        ::= { vlanUndefinedEntry 1 }

    vlanUndefinedNumber OBJECT-TYPE
        SYNTAX          Integer32
        MAX-ACCESS      read-only
        STATUS          current
        DESCRIPTION
            "Undefined VLAN number"
        ::= { vlanUndefinedEntry 2 }

    vlanUndefinedInfo OBJECT-TYPE
        SYNTAX          DisplayString
        MAX-ACCESS      read-only
        STATUS          current
        DESCRIPTION
            "Undefined VLANs detected"
        ::= { vlan 7 }

    vlanUndefinedClear OBJECT-TYPE
        SYNTAX          INTEGER { clear(1) }
        MAX-ACCESS      read-write
        STATUS          current
        DESCRIPTION
            "Clear undefined VLAN information"
        ::= { vlan 8 }

    vlanPoolTable OBJECT-TYPE
        SYNTAX          SEQUENCE OF VlanPoolEntry
        MAX-ACCESS      not-accessible
        STATUS          current
        DESCRIPTION
            "VLAN pool table for the Array"
        ::= { vlan 9 }

    vlanPoolEntry OBJECT-TYPE
        SYNTAX          VlanPoolEntry
        MAX-ACCESS      not-accessible
        STATUS          current
        DESCRIPTION
            "VLAN pool table entry"
        INDEX       { vlanPoolIndex }
        ::= { vlanPoolTable 1 }

    VlanPoolEntry ::= SEQUENCE {
        vlanPoolIndex       Integer32,
        vlanPoolName        DisplayString,
        vlanPoolListMember  Integer32,
        vlanPoolRowStatus   RowStatus
    }

    vlanPoolIndex OBJECT-TYPE
        SYNTAX          Integer32
        MAX-ACCESS      not-accessible
        STATUS          current
        DESCRIPTION
            "VLAN pool table index"
        ::= { vlanPoolEntry 1 }

    vlanPoolName OBJECT-TYPE
        SYNTAX          DisplayString(SIZE(1..20))
        MAX-ACCESS      read-create
        STATUS          current
        DESCRIPTION
            "VLAN pool name"
        ::= { vlanPoolEntry 2 }

    vlanPoolListMember OBJECT-TYPE
        SYNTAX          Integer32(1..4095)
        MAX-ACCESS      read-create
        STATUS          current
        DESCRIPTION
            "VLAN pool list member"
        ::= { vlanPoolEntry 3 }

    vlanPoolRowStatus OBJECT-TYPE
        SYNTAX          RowStatus
        MAX-ACCESS      read-create
        STATUS          current
        DESCRIPTION
            "Status of the VLAN pool row entry"
        ::= { vlanPoolEntry 4 }

    vlanPoolTableReset OBJECT-TYPE
        SYNTAX          INTEGER { reset(1) }
        MAX-ACCESS      read-write
        STATUS          current
        DESCRIPTION
            "Reset VLAN pool table (clear all entries)"
        ::= { vlan 10 }

--
-- CLUSTER
--

    clusterArrayTable OBJECT-TYPE
        SYNTAX          SEQUENCE OF ClusterArrayEntry
        MAX-ACCESS      not-accessible
        STATUS          current
        DESCRIPTION
            "Table of cluster arrays"
        ::= { cluster 1 }

    clusterArrayEntry OBJECT-TYPE
        SYNTAX          ClusterArrayEntry
        MAX-ACCESS      not-accessible
        STATUS          current
        DESCRIPTION
            "Cluster array table entry"
        INDEX       { clusterArrayIndex }
        ::= { clusterArrayTable 1 }

    ClusterArrayEntry ::= SEQUENCE {
        clusterArrayIndex           Integer32,
        clusterArrayHostname        DisplayString,
        clusterArrayIPAddress       IpAddress,
        clusterArrayUsername        DisplayString,
        clusterArrayPassword        DisplayString,
        clusterArrayPasswordForm    INTEGER,
        clusterArrayCluster         DisplayString,
        clusterArrayRowStatus       RowStatus
    }

    clusterArrayIndex OBJECT-TYPE
        SYNTAX          Integer32
        MAX-ACCESS      not-accessible
        STATUS          current
        DESCRIPTION
            "Cluster array table index"
        ::= { clusterArrayEntry 1 }

    clusterArrayHostname OBJECT-TYPE
        SYNTAX          DisplayString(SIZE(1.. 255))
        MAX-ACCESS      read-create
        STATUS          current
        DESCRIPTION
            "Hostname or IP address of the cluster array"
        ::= { clusterArrayEntry 2 }

    clusterArrayIPAddress OBJECT-TYPE
        SYNTAX          IpAddress
        MAX-ACCESS      read-create
        STATUS          current
        DESCRIPTION
            "IP address of the cluster array"
        ::= { clusterArrayEntry 3 }

    clusterArrayUsername OBJECT-TYPE
        SYNTAX          DisplayString(SIZE(0..50))
        MAX-ACCESS      read-create
        STATUS          current
        DESCRIPTION
            "Username for cluster array login"
        ::= { clusterArrayEntry 4 }

    clusterArrayPassword OBJECT-TYPE
        SYNTAX          DisplayString(SIZE(0..100))
        MAX-ACCESS      read-create
        STATUS          current
        DESCRIPTION
            "Password for cluster array login"
        ::= { clusterArrayEntry 5 }

    clusterArrayPasswordForm OBJECT-TYPE
        SYNTAX          INTEGER { clear(0), encrypted(1) }
        MAX-ACCESS      read-create
        STATUS          current
        DESCRIPTION
            "Password form"
        ::= { clusterArrayEntry 6 }

    clusterArrayCluster OBJECT-TYPE
        SYNTAX          DisplayString(SIZE(1..32))
        MAX-ACCESS      read-create
        STATUS          current
        DESCRIPTION
            "Name of the array parent cluster"
        ::= { clusterArrayEntry 7 }

    clusterArrayRowStatus OBJECT-TYPE
        SYNTAX          RowStatus
        MAX-ACCESS      read-create
        STATUS          current
        DESCRIPTION
            "Status of the cluster array row entry"
        ::= { clusterArrayEntry 8 }

    clusterArrayTableReset OBJECT-TYPE
        SYNTAX          INTEGER { reset(1) }
        MAX-ACCESS      read-write
        STATUS          current
        DESCRIPTION
            "Reset cluster array table (clear all entries)"
        ::= { cluster 2 }

--
-- EnvCtrl
--

    envCtrlTemperature OBJECT-TYPE
        SYNTAX          Integer32
        MAX-ACCESS      read-only
        STATUS          current
        DESCRIPTION
            "Outdoor enclosure environmental controller temperature (Celsius)"
        ::= { envCtrl 1 }

    envCtrlHumidity OBJECT-TYPE
        SYNTAX          Integer32
        MAX-ACCESS      read-only
        STATUS          current
        DESCRIPTION
            "Outdoor enclosure environmental controller humidity (percent)"
        ::= { envCtrl 2 }

    envCtrlCoolRPM1 OBJECT-TYPE
        SYNTAX          Integer32
        MAX-ACCESS      read-only
        STATUS          current
        DESCRIPTION
            "Outdoor enclosure environmental controller cooling fan 1 RPM"
        ::= { envCtrl 3 }

    envCtrlCoolRPM2 OBJECT-TYPE
        SYNTAX          Integer32
        MAX-ACCESS      read-only
        STATUS          current
        DESCRIPTION
            "Outdoor enclosure environmental controller cooling fan 2 RPM"
        ::= { envCtrl 4 }

    envCtrlCoolRPM3 OBJECT-TYPE
        SYNTAX          Integer32
        MAX-ACCESS      read-only
        STATUS          current
        DESCRIPTION
            "Outdoor enclosure environmental controller cooling fan 3 RPM"
        ::= { envCtrl 5 }

    envCtrlCoolRPM4 OBJECT-TYPE
        SYNTAX          Integer32
        MAX-ACCESS      read-only
        STATUS          current
        DESCRIPTION
            "Outdoor enclosure environmental controller cooling fan 4 RPM"
        ::= { envCtrl 6 }

    envCtrlHeatRPM1 OBJECT-TYPE
        SYNTAX          Integer32
        MAX-ACCESS      read-only
        STATUS          current
        DESCRIPTION
            "Outdoor enclosure environmental controller heating fan 1 RPM"
        ::= { envCtrl 7 }

    envCtrlHeatRPM2 OBJECT-TYPE
        SYNTAX          Integer32
        MAX-ACCESS      read-only
        STATUS          current
        DESCRIPTION
            "Outdoor enclosure environmental controller heating fan 2 RPM"
        ::= { envCtrl 8 }

    envCtrlArrayOn OBJECT-TYPE
        SYNTAX          INTEGER { off(0), on(1) }
        MAX-ACCESS      read-only
        STATUS          current
        DESCRIPTION
            "Outdoor enclosure environmental controller installed"
        ::= { envCtrl 9 }

    envCtrlCoolOn OBJECT-TYPE
        SYNTAX          INTEGER { off(0), on(1) }
        MAX-ACCESS      read-only
        STATUS          current
        DESCRIPTION
            "Outdoor enclosure environmental controller cooling fan on"
        ::= { envCtrl 10 }

    envCtrlHeatOn OBJECT-TYPE
        SYNTAX          INTEGER { off(0), on(1) }
        MAX-ACCESS      read-only
        STATUS          current
        DESCRIPTION
            "Outdoor enclosure environmental controller heating fan on"
        ::= { envCtrl 11 }

    envCtrlSoftwareVersion OBJECT-TYPE
        SYNTAX          DisplayString
        MAX-ACCESS      read-only
        STATUS          current
        DESCRIPTION
            "Outdoor enclosure environmental controller software version"
        ::= { envCtrl 12 }

--
-- LOCATION
--

    locationReportingOn OBJECT-TYPE
        SYNTAX          INTEGER { disable(0), enable(1) }
        MAX-ACCESS      read-write
        STATUS          current
        DESCRIPTION
            "Location server reporting enable/disable"
        ::= { location 1 }

    locationReportingUrl OBJECT-TYPE
        SYNTAX          DisplayString(SIZE(0..255))
        MAX-ACCESS      read-write
        STATUS          current
        DESCRIPTION
            "Location server URL"
        ::= { location 2 }

    locationReportingKey OBJECT-TYPE
        SYNTAX          DisplayString(SIZE(0..49))
        MAX-ACCESS      read-write
        STATUS          current
        DESCRIPTION
            "Location server key"
        ::= { location 3 }

    locationReportingPeriod OBJECT-TYPE
        SYNTAX          Integer32(15..50000)
        MAX-ACCESS      read-write
        STATUS          current
        DESCRIPTION
            "Location server reporting period"
        ::= { location 4 }

--
-- GROUP
--

    groupTable OBJECT-TYPE
        SYNTAX          SEQUENCE OF GroupEntry
        MAX-ACCESS      not-accessible
        STATUS          current
        DESCRIPTION
            "Group table for the array"
        ::= { group 1 }

    groupEntry OBJECT-TYPE
        SYNTAX          GroupEntry
        MAX-ACCESS      not-accessible
        STATUS          current
        DESCRIPTION
            "Group table entry"
        INDEX       { groupIndex }
        ::= { groupTable 1 }

    GroupEntry ::= SEQUENCE {
        groupIndex                      Integer32,
        groupName                       DisplayString,
        groupRadiusFilterID             DisplayString,
        groupEnable                     INTEGER,
        groupVlan                       Integer32,
        groupQOS                        Integer32,
        groupDhcpPool                   DisplayString,
        groupFilterList                 DisplayString,
        groupRoamingLayer               INTEGER,
        groupStationLimit               Integer32,
        groupTrafficLimit               Integer32,
        groupTrafficLimitSta            Integer32,
        groupTimeOn                     Integer32,
        groupTimeOff                    Integer32,
        groupDaysOnMon                  INTEGER,
        groupDaysOnTue                  INTEGER,
        groupDaysOnWed                  INTEGER,
        groupDaysOnThu                  INTEGER,
        groupDaysOnFri                  INTEGER,
        groupDaysOnSat                  INTEGER,
        groupDaysOnSun                  INTEGER,
        groupWprEnable                  INTEGER,
        groupWprSplashEnable            INTEGER,
        groupWprSplashTimeout           Integer32,
        groupWprLandingPage             DisplayString,
        groupActive                     INTEGER,
        groupRowStatus                  RowStatus,
        groupWprBackground              DisplayString,
        groupWprLogoImage               DisplayString,
        groupWprHeaderText              DisplayString,
        groupWprFooterText              DisplayString,
        groupFallback                   INTEGER,
        groupDeviceID                   DisplayString,
        groupTrafficLimitKbps           Integer32,
        groupTrafficLimitKbpsSta        Integer32,
        groupVlanPool                   DisplayString,
        groupWprServerType              INTEGER,
        groupWprUrl                     DisplayString,
        groupWprSharedSecret            DisplayString,
        groupWprSharedSecretForm        INTEGER,
        groupWprScreenType              INTEGER,
        groupWprHttpsEnable             INTEGER,
        groupWprAuthType                INTEGER,
        groupWprAuthTimeout             Integer32
    }

    groupIndex OBJECT-TYPE
        SYNTAX          Integer32
        MAX-ACCESS      not-accessible
        STATUS          current
        DESCRIPTION
            "Group table index"
        ::= { groupEntry 1 }

    groupName OBJECT-TYPE
        SYNTAX          DisplayString(SIZE(1..32))
        MAX-ACCESS      read-create
        STATUS          current
        DESCRIPTION
            "Group name"
        ::= { groupEntry 2 }

    groupRadiusFilterID OBJECT-TYPE
        SYNTAX          DisplayString(SIZE(0..32))
        MAX-ACCESS      read-create
        STATUS          current
        DESCRIPTION
            "Radius Filter-ID (Attribute Type 11) mapped to this group"
        ::= { groupEntry 3 }

    groupEnable OBJECT-TYPE
        SYNTAX          INTEGER { disable(0), enable(1) }
        MAX-ACCESS      read-create
        STATUS          current
        DESCRIPTION
            "Enable or disable group"
        ::= { groupEntry 4 }

    groupVlan OBJECT-TYPE
        SYNTAX          Integer32(0..65535)
        MAX-ACCESS      read-create
        STATUS          current
        DESCRIPTION
            "Group VLAN ID"
        ::= { groupEntry 5 }

    groupQOS OBJECT-TYPE
        SYNTAX          Integer32(0..3)
        MAX-ACCESS      read-create
        STATUS          current
        DESCRIPTION
            "Group QoS level"
        ::= { groupEntry 6 }

    groupDhcpPool OBJECT-TYPE
        SYNTAX          DisplayString(SIZE(0..20))
        MAX-ACCESS      read-create
        STATUS          current
        DESCRIPTION
            "Group DHCP pool"
        ::= { groupEntry 7 }

    groupFilterList OBJECT-TYPE
        SYNTAX          DisplayString(SIZE(0..20))
        MAX-ACCESS      read-create
        STATUS          current
        DESCRIPTION
            "Group filter list"
        ::= { groupEntry 8 }

    groupRoamingLayer OBJECT-TYPE
        SYNTAX          INTEGER { layer-2-only(0), layer-2-and-3(1), none(2) }
        MAX-ACCESS      read-create
        STATUS          current
        DESCRIPTION
            "Fast roaming layer allowed for this group"
        ::= { groupEntry 9 }

    groupStationLimit OBJECT-TYPE
        SYNTAX          Integer32(1..3840)
        MAX-ACCESS      read-create
        STATUS          current
        DESCRIPTION
            "Station limit for group"
        ::= { groupEntry 10 }

    groupTrafficLimit OBJECT-TYPE
        SYNTAX          Integer32(0..1000000)
        MAX-ACCESS      read-create
        STATUS          current
        DESCRIPTION
            "Traffic limit for group (10 to 1000000 pps, 0 - unlimited)"
        ::= { groupEntry 11 }

    groupTrafficLimitSta OBJECT-TYPE
        SYNTAX          Integer32(0..100000)
        MAX-ACCESS      read-create
        STATUS          current
        DESCRIPTION
            "Traffic limit per station for group (10 to 100000 pps, 0 - unlimited)"
        ::= { groupEntry 12 }

    groupTimeOn OBJECT-TYPE
        SYNTAX          Integer32(-1..1439)
        MAX-ACCESS      read-create
        STATUS          current
        DESCRIPTION
            "Set daily time group is active (in minutes, -1 - always)"
        ::= { groupEntry 13 }

    groupTimeOff OBJECT-TYPE
        SYNTAX          Integer32(-1..1439)
        MAX-ACCESS      read-create
        STATUS          current
        DESCRIPTION
            "Set daily time group is inactive (in minutes, -1 - never)"
        ::= { groupEntry 14 }

    groupDaysOnMon OBJECT-TYPE
        SYNTAX          INTEGER { off(0), on(1) }
        MAX-ACCESS      read-create
        STATUS          current
        DESCRIPTION
            "Group is on/off on Monday"
        ::= { groupEntry 15 }

    groupDaysOnTue OBJECT-TYPE
        SYNTAX          INTEGER { off(0), on(1) }
        MAX-ACCESS      read-create
        STATUS          current
        DESCRIPTION
            "Group is on/off on Tuesday"
        ::= { groupEntry 16 }

    groupDaysOnWed OBJECT-TYPE
        SYNTAX          INTEGER { off(0), on(1) }
        MAX-ACCESS      read-create
        STATUS          current
        DESCRIPTION
            "Group is on/off on Wednesday"
        ::= { groupEntry 17 }

    groupDaysOnThu OBJECT-TYPE
        SYNTAX          INTEGER { off(0), on(1) }
        MAX-ACCESS      read-create
        STATUS          current
        DESCRIPTION
            "Group is on/off on Thursday"
        ::= { groupEntry 18 }

    groupDaysOnFri OBJECT-TYPE
        SYNTAX          INTEGER { off(0), on(1) }
        MAX-ACCESS      read-create
        STATUS          current
        DESCRIPTION
            "Group is on/off on Friday"
        ::= { groupEntry 19 }

    groupDaysOnSat OBJECT-TYPE
        SYNTAX          INTEGER { off(0), on(1) }
        MAX-ACCESS      read-create
        STATUS          current
        DESCRIPTION
            "Group is on/off on Saturday"
        ::= { groupEntry 20 }

    groupDaysOnSun OBJECT-TYPE
        SYNTAX          INTEGER { off(0), on(1) }
        MAX-ACCESS      read-create
        STATUS          current
        DESCRIPTION
            "Group is on/off on Sunday"
        ::= { groupEntry 21 }

    groupWprEnable OBJECT-TYPE
        SYNTAX          INTEGER { disable(0), enable(1) }
        MAX-ACCESS      read-create
        STATUS          current
        DESCRIPTION
            "Enable or disable WPR for group"
        ::= { groupEntry 22 }

    groupWprSplashEnable OBJECT-TYPE
        SYNTAX          INTEGER { disable(0), enable(1) }
        MAX-ACCESS      read-create
        STATUS          current
        DESCRIPTION
            "Enable or disable splash screen for WPR"
        ::= { groupEntry 23 }

    groupWprSplashTimeout OBJECT-TYPE
        SYNTAX          Integer32(0..100)
        MAX-ACCESS      read-create
        STATUS          current
        DESCRIPTION
            "Splash screen timeout (0 - no timeout)"
        ::= { groupEntry 24 }

    groupWprLandingPage OBJECT-TYPE
        SYNTAX          DisplayString(SIZE(0..255))
        MAX-ACCESS      read-create
        STATUS          current
        DESCRIPTION
            "Landing page URL for WPR"
        ::= { groupEntry 25 }

    groupActive OBJECT-TYPE
        SYNTAX          INTEGER { inactive(0), active(1) }
        MAX-ACCESS      read-only
        STATUS          current
        DESCRIPTION
            "Flag indicating whether group is currently active"
        ::= { groupEntry 26 }

    groupRowStatus OBJECT-TYPE
        SYNTAX          RowStatus
        MAX-ACCESS      read-create
        STATUS          current
        DESCRIPTION
            "Status of the group row entry"
        ::= { groupEntry 27 }

    groupWprBackground OBJECT-TYPE
        SYNTAX          DisplayString(SIZE(0..50))
        MAX-ACCESS      read-write
        STATUS          current
        DESCRIPTION
            "Custom background file for WPR"
        ::= { groupEntry 28 }

    groupWprLogoImage OBJECT-TYPE
        SYNTAX          DisplayString(SIZE(0..50))
        MAX-ACCESS      read-write
        STATUS          current
        DESCRIPTION
            "Custom logo file for WPR"
        ::= { groupEntry 29 }

    groupWprHeaderText OBJECT-TYPE
        SYNTAX          DisplayString(SIZE(0..50))
        MAX-ACCESS      read-write
        STATUS          current
        DESCRIPTION
            "Custom header text file for WPR"
        ::= { groupEntry 30 }

    groupWprFooterText OBJECT-TYPE
        SYNTAX          DisplayString(SIZE(0..50))
        MAX-ACCESS      read-write
        STATUS          current
        DESCRIPTION
            "Custom footer text file for WPR"
        ::= { groupEntry 31 }

    groupFallback OBJECT-TYPE
        SYNTAX          INTEGER { none(0), disable-group(1) }
        MAX-ACCESS      read-create
        STATUS          current
        DESCRIPTION
            "Define network connectivity fallback mode for this group"
        ::= { groupEntry 32 }

    groupDeviceID OBJECT-TYPE
        SYNTAX          DisplayString(SIZE(1..32))
        MAX-ACCESS      read-create
        STATUS          current
        DESCRIPTION
            "Device ID mapped to this group"
        ::= { groupEntry 33 }

    groupTrafficLimitKbps OBJECT-TYPE
        SYNTAX          Integer32(0..4000000)
        MAX-ACCESS      read-create
        STATUS          current
        DESCRIPTION
            "Traffic limit for group (10 to 4000000 kbps, 0 - unlimited)"
        ::= { groupEntry 34 }

    groupTrafficLimitKbpsSta OBJECT-TYPE
        SYNTAX          Integer32(0..400000)
        MAX-ACCESS      read-create
        STATUS          current
        DESCRIPTION
            "Traffic limit per station for group (10 to 400000 kbps, 0 - unlimited)"
        ::= { groupEntry 35 }

    groupVlanPool OBJECT-TYPE
        SYNTAX          DisplayString(SIZE(0..20))
        MAX-ACCESS      read-create
        STATUS          current
        DESCRIPTION
            "Group VLAN pool"
        ::= { groupEntry 36 }

    groupWprServerType OBJECT-TYPE
        SYNTAX          INTEGER { external(0), internal(1) }
        MAX-ACCESS      read-create
        STATUS          current
        DESCRIPTION
            "Server type for WPR"
        ::= { groupEntry 37 }

    groupWprUrl OBJECT-TYPE
        SYNTAX          DisplayString(SIZE(0..255))
        MAX-ACCESS      read-create
        STATUS          current
        DESCRIPTION
            "URL for WPR"
        ::= { groupEntry 38 }

    groupWprSharedSecret OBJECT-TYPE
        SYNTAX          DisplayString(SIZE(0..128))
        MAX-ACCESS      read-create
        STATUS          current
        DESCRIPTION
            "Shared secret for WPR"
        ::= { groupEntry 39 }

    groupWprSharedSecretForm OBJECT-TYPE
        SYNTAX          INTEGER { clear(0), encrypted(1) }
        MAX-ACCESS      read-create
        STATUS          current
        DESCRIPTION
            "WPR shared secret form"
        ::= { groupEntry 40 }

    groupWprScreenType OBJECT-TYPE
        SYNTAX          INTEGER { splash(0), login(1), none(2) }
        MAX-ACCESS      read-create
        STATUS          current
        DESCRIPTION
            "Screen type for WPR"
        ::= { groupEntry 41 }

    groupWprHttpsEnable OBJECT-TYPE
        SYNTAX          INTEGER { disable(0), enable(1) }
        MAX-ACCESS      read-create
        STATUS          current
        DESCRIPTION
            "Enable or disable HTTPS login for WPR"
        ::= { groupEntry 42 }

    groupWprAuthType OBJECT-TYPE
        SYNTAX          INTEGER { chap(0), pap(1), ms-chap(2) }
        MAX-ACCESS      read-create
        STATUS          current
        DESCRIPTION
            "WPR authentication protocol"
        ::= { groupEntry 43 }

    groupWprAuthTimeout OBJECT-TYPE
        SYNTAX          Integer32(0..10080)
        MAX-ACCESS      read-create
        STATUS          current
        DESCRIPTION
            "WPR station authentication timeout in minutes (0 - no timeout)"
        ::= { groupEntry 44 }

    groupTableReset OBJECT-TYPE
        SYNTAX          INTEGER { reset(1) }
        MAX-ACCESS      read-write
        STATUS          current
        DESCRIPTION
            "Reset group table (clear all entries)"
        ::= { group 2 }

--
-- MDM
--

    mdmAirWatchApiURL OBJECT-TYPE
        SYNTAX          DisplayString(SIZE(0..255))
        MAX-ACCESS      read-write
        STATUS          current
        DESCRIPTION
            "AirWatch API URL"
        ::= { mdm 1 }

    mdmAirWatchApiKey OBJECT-TYPE
        SYNTAX          DisplayString(SIZE(0..50))
        MAX-ACCESS      read-write
        STATUS          current
        DESCRIPTION
            "AirWatch API key"
        ::= { mdm 2 }

    mdmAirWatchApiUsername OBJECT-TYPE
        SYNTAX          DisplayString(SIZE(0..50))
        MAX-ACCESS      read-write
        STATUS          current
        DESCRIPTION
            "AirWatch API username"
        ::= { mdm 3 }

    mdmAirWatchApiPassword OBJECT-TYPE
        SYNTAX          DisplayString(SIZE(0..50))
        MAX-ACCESS      read-write
        STATUS          current
        DESCRIPTION
            "AirWatch API password"
        ::= { mdm 4 }

    mdmAirWatchApiPasswordEnc OBJECT-TYPE
        SYNTAX          DisplayString(SIZE(0..100))
        MAX-ACCESS      read-write
        STATUS          current
        DESCRIPTION
            "AirWatch API password (encrypted)"
        ::= { mdm 5 }

    mdmAirWatchApiTimeout OBJECT-TYPE
        SYNTAX          Integer32(1..20)
        MAX-ACCESS      read-write
        STATUS          current
        DESCRIPTION
            "AirWatch API timeout (in seconds)"
        ::= { mdm 6 }

    mdmAirWatchApiPollPeriod OBJECT-TYPE
        SYNTAX          Integer32(1..3600)
        MAX-ACCESS      read-write
        STATUS          current
        DESCRIPTION
            "AirWatch API poll period (in seconds)"
        ::= { mdm 7 }

    mdmAirWatchApiAccessError OBJECT-TYPE
        SYNTAX          INTEGER { block(0), allow(1) }
        MAX-ACCESS      read-write
        STATUS          current
        DESCRIPTION
            "AirWatch API access error action"
        ::= { mdm 8 }

    mdmAirWatchRedirectURL OBJECT-TYPE
        SYNTAX          DisplayString(SIZE(0..255))
        MAX-ACCESS      read-write
        STATUS          current
        DESCRIPTION
            "AirWatch station redirect URL"
        ::= { mdm 9 }

--
-- NETFLOW
--

    netflowEnable OBJECT-TYPE
        SYNTAX          INTEGER { disable(0), v5(1), v9(2), ipfix(3) }
        MAX-ACCESS      read-write
        STATUS          current
        DESCRIPTION
            "Enable or disable NetFlow probe"
        ::= { netflow 1 }

    netflowCollectorHost OBJECT-TYPE
        SYNTAX          DisplayString(SIZE(0.. 255))
        MAX-ACCESS      read-write
        STATUS          current
        DESCRIPTION
            "Netflow collector IP address or hostname"
        ::= { netflow 2 }

    netflowCollectorPort OBJECT-TYPE
        SYNTAX          Integer32(0..65535)
        MAX-ACCESS      read-write
        STATUS          current
        DESCRIPTION
            "NetFlow collector port"
        ::= { netflow 3 }

--
-- WIFI_TAG
--

    wifiTagEnable OBJECT-TYPE
        SYNTAX          INTEGER { disable(0), enable(1) }
        MAX-ACCESS      read-write
        STATUS          current
        DESCRIPTION
            "Enable or disable WiFi Tag"
        ::= { wifiTag 1 }

    wifiTagUdpPort OBJECT-TYPE
        SYNTAX          Integer32(0..65535)
        MAX-ACCESS      read-write
        STATUS          current
        DESCRIPTION
            "WiFi Tag UDP Port"
        ::= { wifiTag 2 }

    wifiTagChannel1 OBJECT-TYPE
        SYNTAX          Integer32(0..255)
        MAX-ACCESS      read-write
        STATUS          current
        DESCRIPTION
            "WiFi Tag Channel 1"
        ::= { wifiTag 3 }

    wifiTagChannel2 OBJECT-TYPE
        SYNTAX          Integer32(0..255)
        MAX-ACCESS      read-write
        STATUS          current
        DESCRIPTION
            "WiFi Tag Channel 2"
        ::= { wifiTag 4 }

    wifiTagChannel3 OBJECT-TYPE
        SYNTAX          Integer32(0..255)
        MAX-ACCESS      read-write
        STATUS          current
        DESCRIPTION
            "WiFi Tag Channel 3"
        ::= { wifiTag 5 }

    wifiTagEkahauServer OBJECT-TYPE
        SYNTAX          DisplayString(SIZE(0.. 255))
        MAX-ACCESS      read-write
        STATUS          current
        DESCRIPTION
            "Ekahau server host name or IP address"
        ::= { wifiTag 6 }

--
-- WPR
--

    wprWhitelistSsidTable OBJECT-TYPE
        SYNTAX          SEQUENCE OF WprWhitelistSsidEntry
        MAX-ACCESS      not-accessible
        STATUS          current
        DESCRIPTION
            "WPR whitelist per SSID"
        ::= { wpr 1 }

    wprWhitelistSsidEntry OBJECT-TYPE
        SYNTAX          WprWhitelistSsidEntry
        MAX-ACCESS      not-accessible
        STATUS          current
        DESCRIPTION
            "WPR whitelist per SSID table entry"
        INDEX       { wprWhitelistSsidIndex }
        ::= { wprWhitelistSsidTable 1 }

    WprWhitelistSsidEntry ::= SEQUENCE {
        wprWhitelistSsidIndex           Integer32,
        wprWhitelistSsidDomain          DisplayString,
        wprWhitelistSsidName            DisplayString,
        wprWhitelistSsidRowStatus       RowStatus
    }

    wprWhitelistSsidIndex OBJECT-TYPE
        SYNTAX          Integer32
        MAX-ACCESS      not-accessible
        STATUS          current
        DESCRIPTION
            "WPR whitelist per SSID index"
        ::= { wprWhitelistSsidEntry 1 }

    wprWhitelistSsidDomain OBJECT-TYPE
        SYNTAX          DisplayString(SIZE(1..255))
        MAX-ACCESS      read-create
        STATUS          current
        DESCRIPTION
            "WPR whitelist domain name"
        ::= { wprWhitelistSsidEntry 2 }

    wprWhitelistSsidName OBJECT-TYPE
        SYNTAX          DisplayString(SIZE(1..32))
        MAX-ACCESS      read-create
        STATUS          current
        DESCRIPTION
            "SSID this WPR whitelist domain belongs to"
        ::= { wprWhitelistSsidEntry 3 }

    wprWhitelistSsidRowStatus OBJECT-TYPE
        SYNTAX          RowStatus
        MAX-ACCESS      read-create
        STATUS          current
        DESCRIPTION
            "Status of the WPR whitelist row entry"
        ::= { wprWhitelistSsidEntry 4 }

    wprWhitelistGroupTable OBJECT-TYPE
        SYNTAX          SEQUENCE OF WprWhitelistGroupEntry
        MAX-ACCESS      not-accessible
        STATUS          current
        DESCRIPTION
            "WPR whitelist per user group"
        ::= { wpr 2 }

    wprWhitelistGroupEntry OBJECT-TYPE
        SYNTAX          WprWhitelistGroupEntry
        MAX-ACCESS      not-accessible
        STATUS          current
        DESCRIPTION
            "WPR whitelist per user group table entry"
        INDEX       { wprWhitelistGroupIndex }
        ::= { wprWhitelistGroupTable 1 }

    WprWhitelistGroupEntry ::= SEQUENCE {
        wprWhitelistGroupIndex          Integer32,
        wprWhitelistGroupDomain         DisplayString,
        wprWhitelistGroupName           DisplayString,
        wprWhitelistGroupRowStatus      RowStatus
    }

    wprWhitelistGroupIndex OBJECT-TYPE
        SYNTAX          Integer32
        MAX-ACCESS      not-accessible
        STATUS          current
        DESCRIPTION
            "WPR whitelist per user group index"
        ::= { wprWhitelistGroupEntry 1 }

    wprWhitelistGroupDomain OBJECT-TYPE
        SYNTAX          DisplayString(SIZE(1..255))
        MAX-ACCESS      read-create
        STATUS          current
        DESCRIPTION
            "WPR whitelist domain name"
        ::= { wprWhitelistGroupEntry 2 }

    wprWhitelistGroupName OBJECT-TYPE
        SYNTAX          DisplayString(SIZE(1..32))
        MAX-ACCESS      read-create
        STATUS          current
        DESCRIPTION
            "User group this WPR whitelist domain belongs to"
        ::= { wprWhitelistGroupEntry 3 }

    wprWhitelistGroupRowStatus OBJECT-TYPE
        SYNTAX          RowStatus
        MAX-ACCESS      read-create
        STATUS          current
        DESCRIPTION
            "Status of the WPR whitelist row entry"
        ::= { wprWhitelistGroupEntry 4 }

    wprWhitelistSsidTableReset OBJECT-TYPE
        SYNTAX          DisplayString(SIZE(1..32))
        MAX-ACCESS      read-write
        STATUS          current
        DESCRIPTION
            "Reset WPR whitelist (clear all entries) for given SSID"
        ::= { wpr 3 }

    wprWhitelistGroupTableReset OBJECT-TYPE
        SYNTAX          DisplayString(SIZE(1..32))
        MAX-ACCESS      read-write
        STATUS          current
        DESCRIPTION
            "Reset WPR whitelist (clear all entries) for given user group"
        ::= { wpr 4 }

--
-- OAUTH - Open Authentication
--

    oauthTokenTable OBJECT-TYPE
        SYNTAX          SEQUENCE OF OauthTokenEntry
        MAX-ACCESS      not-accessible
        STATUS          current
        DESCRIPTION
            "OAUTH Token table"
        ::= { oauth 1 }

    oauthTokenEntry OBJECT-TYPE
        SYNTAX          OauthTokenEntry
        MAX-ACCESS      not-accessible
        STATUS          current
        DESCRIPTION
            "OAUTH token table entry"
        INDEX       { oauthTokenIndex }
        ::= { oauthTokenTable 1 }

    OauthTokenEntry ::= SEQUENCE {
        oauthTokenIndex         Integer32,
        oauthTokenId            DisplayString,
        oauthTokenClientId      DisplayString,
        oauthTokenGrantType     DisplayString,
        oauthTokenExpiration    Counter32,
        oauthTokenUserAgent     DisplayString,
        oauthTokenScope         DisplayString,
        oauthTokenCode          DisplayString,
        oauthTokenType          DisplayString,
        oauthTokenRowStatus     RowStatus
    }

    oauthTokenIndex OBJECT-TYPE
        SYNTAX          Integer32
        MAX-ACCESS      not-accessible
        STATUS          current
        DESCRIPTION
            "OAUTH Token index"
        ::= { oauthTokenEntry 1 }


    oauthTokenId OBJECT-TYPE
        SYNTAX          DisplayString(SIZE(1..50))
        MAX-ACCESS      read-only
        STATUS          current
        DESCRIPTION
            "OAUTH Token Id"
        ::= { oauthTokenEntry 2 }

    oauthTokenClientId OBJECT-TYPE
        SYNTAX          DisplayString(SIZE(1..50))
        MAX-ACCESS      read-only
        STATUS          current
        DESCRIPTION
            "OAUTH Token Client ID"
        ::= { oauthTokenEntry 3 }

    oauthTokenGrantType OBJECT-TYPE
        SYNTAX          DisplayString(SIZE(1..50))
        MAX-ACCESS      read-only
        STATUS          current
        DESCRIPTION
            "OAUTH Token Grant Type"
        ::= { oauthTokenEntry 4 }

    oauthTokenExpiration OBJECT-TYPE
        SYNTAX          Counter32
        MAX-ACCESS      read-only
        STATUS          current
        DESCRIPTION
            "OAUTH Token Expiration"
        ::= { oauthTokenEntry 5 }

    oauthTokenUserAgent OBJECT-TYPE
        SYNTAX          DisplayString(SIZE(1..50))
        MAX-ACCESS      read-only
        STATUS          current
        DESCRIPTION
            "OAUTH Token User Agent"
        ::= { oauthTokenEntry 6 }

    oauthTokenScope OBJECT-TYPE
        SYNTAX          DisplayString(SIZE(1..50))
        MAX-ACCESS      read-only
        STATUS          current
        DESCRIPTION
            "OAUTH Token Scope"
        ::= { oauthTokenEntry 7 }

    oauthTokenCode OBJECT-TYPE
        SYNTAX          DisplayString(SIZE(1..50))
        MAX-ACCESS      read-only
        STATUS          current
        DESCRIPTION
            "OAUTH Token Code"
        ::= { oauthTokenEntry 8 }

    oauthTokenType OBJECT-TYPE
        SYNTAX          DisplayString(SIZE(1..50))
        MAX-ACCESS      read-only
        STATUS          current
        DESCRIPTION
            "OAUTH Token Type"
        ::= { oauthTokenEntry 9 }

    oauthTokenRowStatus OBJECT-TYPE
        SYNTAX          RowStatus
        MAX-ACCESS      read-write
        STATUS          current
        DESCRIPTION
            "Status of the OAUTH Token row entry"
        ::= { oauthTokenEntry 10 }

    oauthTableReset OBJECT-TYPE
        SYNTAX          INTEGER { reset(1) }
        MAX-ACCESS      read-write
        STATUS          current
        DESCRIPTION
            "Reset OAUTH table (clear all entries)"
        ::= { oauth 2 }

--
-- PROXY FORWARDING
--

    proxyFwdProxyType OBJECT-TYPE
        SYNTAX          INTEGER { off(0), bluecoat(1), netboxblue(2) }
        MAX-ACCESS      read-write
        STATUS          current
        DESCRIPTION
            "Disable or enable proxy forwarding"
        ::= { proxyFwd 1 }

    proxyFwdBlueCoatUrl OBJECT-TYPE
        SYNTAX          DisplayString(SIZE(0.. 255))
        MAX-ACCESS      read-write
        STATUS          current
        DESCRIPTION
            "URL of BlueCoat proxy server"
        ::= { proxyFwd 2 }

    proxyFwdNetBoxBlueUrl OBJECT-TYPE
        SYNTAX          DisplayString(SIZE(0.. 255))
        MAX-ACCESS      read-write
        STATUS          current
        DESCRIPTION
            "URL of NetBoxBlue proxy server"
        ::= { proxyFwd 3 }

--
-- LLDP
--

    lldpEnable OBJECT-TYPE
        SYNTAX          INTEGER { disable(0), enable(1) }
        MAX-ACCESS      read-write
        STATUS          current
        DESCRIPTION
            "Enable or disable LLDP"
        ::= { lldp 1 }

    lldpInterval OBJECT-TYPE
        SYNTAX          Integer32(5..900)
        MAX-ACCESS      read-write
        STATUS          current
        DESCRIPTION
            "LLDP message interval (in seconds)"
        ::= { lldp 2 }

    lldpHoldTime OBJECT-TYPE
        SYNTAX          Integer32(10..255)
        MAX-ACCESS      read-write
        STATUS          current
        DESCRIPTION
            "LLDP message hold time (in seconds)"
        ::= { lldp 3 }

    lldpRequestPower OBJECT-TYPE
        SYNTAX          INTEGER { disable(0), enable(1) }
        MAX-ACCESS      read-write
        STATUS          current
        DESCRIPTION
            "Enable or disable LLDP power request"
        ::= { lldp 4 }

--
-- POSITION INFO
--

    positionInfoX OBJECT-TYPE
        SYNTAX          DisplayString
        MAX-ACCESS      read-write
        STATUS          current
        DESCRIPTION
            "System X coordinate (float converted to string)"
        ::= { position 1 }

    positionInfoY OBJECT-TYPE
        SYNTAX          DisplayString
        MAX-ACCESS      read-write
        STATUS          current
        DESCRIPTION
            "System Y coordinate (float converted to string)"
        ::= { position 2 }

    positionInfoZ OBJECT-TYPE
        SYNTAX          DisplayString
        MAX-ACCESS      read-write
        STATUS          current
        DESCRIPTION
            "System Z coordinate (float converted to string)"
        ::= { position 3 }

    positionInfoScale OBJECT-TYPE
        SYNTAX          DisplayString
        MAX-ACCESS      read-write
        STATUS          current
        DESCRIPTION
            "System scale (feet/unit) (float converted to string)"
        ::= { position 4 }

    positionInfoAngle OBJECT-TYPE
        SYNTAX          DisplayString
        MAX-ACCESS      read-write
        STATUS          current
        DESCRIPTION
            "System angle (degrees from north) (float converted to string)"
        ::= { position 5 }

    positionInfoMount OBJECT-TYPE
        SYNTAX          INTEGER { face-down(0), face-up(1) }
        MAX-ACCESS      read-write
        STATUS          current
        DESCRIPTION
            "System mounting orientation"
        ::= { position 6 }

    positionInfoScope OBJECT-TYPE
        SYNTAX          INTEGER { map(0), global(1) }
        MAX-ACCESS      read-write
        STATUS          current
        DESCRIPTION
            "System location scope"
        ::= { position 7 }

    positionInfoMap OBJECT-TYPE
        SYNTAX          DisplayString
        MAX-ACCESS      read-write
        STATUS          current
        DESCRIPTION
            "System location map"
        ::= { position 8 }

--
-- TRAPS
--

    adminTraps          OBJECT IDENTIFIER ::= { traps 1 }
    stationTraps        OBJECT IDENTIFIER ::= { traps 2 }
    generalTraps        OBJECT IDENTIFIER ::= { traps 3 }
    envCtrlTraps        OBJECT IDENTIFIER ::= { traps 4 }
    iapTraps            OBJECT IDENTIFIER ::= { traps 5 }
    trapObjects         OBJECT IDENTIFIER ::= { traps 100 }

--
--  TRAPS ADMIN
--

    adminLogin NOTIFICATION-TYPE
        OBJECTS         { adminUsername }
        STATUS          current
        DESCRIPTION
            "Admin Logged into Array"
        ::= { adminTraps 1 }

    adminLogout NOTIFICATION-TYPE
        OBJECTS         { adminUsername }
        STATUS          current
        DESCRIPTION
            "Admin Logged out from Array"
        ::= { adminTraps 2 }

--
-- TRAPS STATION
--

    stationACLFailure NOTIFICATION-TYPE
        OBJECTS         { stationAssociationMACAddress }
        STATUS          current
        DESCRIPTION
            "Station rejected by ACL"
        ::= { stationTraps 1 }

    stationRadiusAuthFailure NOTIFICATION-TYPE
        OBJECTS         { stationAssociationMACAddress }
        STATUS          current
        DESCRIPTION
            "Station failed Radius server authentication"
        ::= { stationTraps 2 }

--
-- TRAPS GENERAL
--
    resetArray NOTIFICATION-TYPE
        STATUS          current
        DESCRIPTION
            "Admin requested reset of the Array"
        ::= { generalTraps 1 }

    rebootArray NOTIFICATION-TYPE
        STATUS          current
        DESCRIPTION
            "Administrator requested a reboot of Array"
        ::= { generalTraps 2 }

    softwareUploadFailure NOTIFICATION-TYPE
        STATUS          current
        DESCRIPTION
            "Array software image upload failed"
        ::= { generalTraps 3 }

    softwareUploadSuccess NOTIFICATION-TYPE
        STATUS          current
        DESCRIPTION
            "Array software image upload succeeded"
        ::= { generalTraps 4 }

    softwareUpgradeFailure NOTIFICATION-TYPE
        STATUS          current
        DESCRIPTION
            "Array software upgrade failed"
        ::= { generalTraps 5 }

    softwareUpgradeSuccess NOTIFICATION-TYPE
        STATUS          current
        DESCRIPTION
            "Array software upgrade succeeded"
        ::= { generalTraps 6 }

    dhcpRenewFailure NOTIFICATION-TYPE
        OBJECTS         { ethStatsIfaceName }
        STATUS          current
        DESCRIPTION
            "Unable to get DHCP Address"
        ::= { generalTraps 7 }

    cfgChange NOTIFICATION-TYPE
        OBJECTS         { cfgModuleOID }
        STATUS          current
        DESCRIPTION
            "Configuration change"
        ::= { generalTraps 8 }

    keepAlive NOTIFICATION-TYPE
        OBJECTS         { systemHostname }
        STATUS          current
        DESCRIPTION
            "Keepalive notice"
        ::= { generalTraps 9 }

    encDoorOpened NOTIFICATION-TYPE
        STATUS          current
        DESCRIPTION
            "Enclosure door opened"
        ::= { generalTraps 10 }

    encDoorClosed NOTIFICATION-TYPE
        STATUS          current
        DESCRIPTION
            "Enclosure door closed"
        ::= { generalTraps 11 }

    flashPartitionCorrupt NOTIFICATION-TYPE
        STATUS          current
        DESCRIPTION
            "Flash partition corrupt"
        ::= { generalTraps 12 }

    licenseUpdate NOTIFICATION-TYPE
        STATUS          current
        DESCRIPTION
            "License updated"
        ::= { generalTraps 13 }

    radioMixInvalid NOTIFICATION-TYPE
        STATUS          current
        DESCRIPTION
            "Invalid Radio Mix"
        ::= { generalTraps 14 }

--
-- TRAPS ENVIRONMENTAL CONTROLLER
--

    envCtrlTempOver NOTIFICATION-TYPE
        STATUS          current
        DESCRIPTION
            "Outdoor enclosure temperature too high"
        ::= { envCtrlTraps 1 }

    envCtrlTempUnder NOTIFICATION-TYPE
        STATUS          current
        DESCRIPTION
            "Outdoor enclosure temperature too low"
        ::= { envCtrlTraps 2 }

    envCtrlHumidOver NOTIFICATION-TYPE
        STATUS          current
        DESCRIPTION
            "Outdoor enclosure humidity too high"
        ::= { envCtrlTraps 3 }

    envCtrlFanFail NOTIFICATION-TYPE
        STATUS          current
        DESCRIPTION
            "Outdoor enclosure fan failure"
        ::= { envCtrlTraps 4 }

--
-- TRAPS IAP
--

    iapBeaconProbeFailure NOTIFICATION-TYPE
        OBJECTS         { iapStatsIfaceName }
        STATUS          current
        DESCRIPTION
            "No received beacons (or probe responses) from IAP, alert only"
        ::= { iapTraps 1 }

    iapBeaconProbeFailurePhyReset NOTIFICATION-TYPE
        OBJECTS         { iapStatsIfaceName }
        STATUS          current
        DESCRIPTION
            "No received beacons (or probe responses) from IAP, resetting interface PHY"
        ::= { iapTraps 2 }

    iapBeaconProbeFailureMacReset NOTIFICATION-TYPE
        OBJECTS         { iapStatsIfaceName }
        STATUS          current
        DESCRIPTION
            "No received beacons (or probe responses) from IAP, resetting interface MAC"
        ::= { iapTraps 3 }

    iapBeaconProbeFailureArrayReboot NOTIFICATION-TYPE
        OBJECTS         { iapStatsIfaceName }
        STATUS          current
        DESCRIPTION
            "No received beacons (or probe responses) from IAP, scheduling array reboot"
        ::= { iapTraps 4 }

--
--
-- TRAP OBJECTS
--

    cfgModuleOID OBJECT-TYPE
        SYNTAX          OBJECT IDENTIFIER
        MAX-ACCESS      accessible-for-notify
        STATUS          current
        DESCRIPTION
            "Configuration module OID"
        ::= { trapObjects 1 }

--
-- PROXY CLIENT for MANAGEMENT TRAFFIC (PROXY MGMT)
--
    proxyMgmtEnabled OBJECT-TYPE
        SYNTAX          INTEGER { disable(0), enable(1) }
        MAX-ACCESS      read-write
        STATUS          current
        DESCRIPTION
            "Disable or enable all proxy client services for management traffic"
        ::= { proxyMgmt 1 }

    proxyMgmtCustom OBJECT-TYPE
        SYNTAX          INTEGER { disable(0), enable(1) }
        MAX-ACCESS      read-write
        STATUS          current
        DESCRIPTION
            "Disable or enable custom tsocks configuration for proxy client"
        ::= { proxyMgmt 2 }

   proxyMgmtHttpEnabled OBJECT-TYPE
        SYNTAX          INTEGER { disable(0), enable(1) }
        MAX-ACCESS      read-write
        STATUS          current
        DESCRIPTION
            "Disable or enable HTTP proxy client"
        ::= { proxyMgmt 3 }
        
   proxyMgmtHttpHost OBJECT-TYPE
        SYNTAX          DisplayString
        MAX-ACCESS      read-write
        STATUS          current
        DESCRIPTION
            "Hostname used with HTTP proxy client"
        ::= { proxyMgmt 4 }

   proxyMgmtHttpPort OBJECT-TYPE
        SYNTAX          Integer32
        MAX-ACCESS      read-write
        STATUS          current
        DESCRIPTION
            "Port used with HTTP proxy client"
        ::= { proxyMgmt 5 }

   proxyMgmtHttpUsername OBJECT-TYPE
        SYNTAX          DisplayString
        MAX-ACCESS      read-write
        STATUS          current
        DESCRIPTION
            "Username used with HTTP proxy client"
        ::= { proxyMgmt 6 }

   proxyMgmtHttpPassword OBJECT-TYPE
        SYNTAX          DisplayString
        MAX-ACCESS      read-write
        STATUS          current
        DESCRIPTION
            "Password used with HTTP proxy client"
        ::= { proxyMgmt 7 }

   proxyMgmtHttpType OBJECT-TYPE
        SYNTAX          INTEGER { http(0) }
        MAX-ACCESS      read-write
        STATUS          current
        DESCRIPTION
            "HTTP proxy client Type"
        ::= { proxyMgmt 8 }

   proxyMgmtHttpsEnabled OBJECT-TYPE
        SYNTAX          INTEGER { disable(0), enable(1) }
        MAX-ACCESS      read-write
        STATUS          current
        DESCRIPTION
            "Disable or enable HTTPS proxy client"
        ::= { proxyMgmt 9 }
        
   proxyMgmtHttpsHost OBJECT-TYPE
        SYNTAX          DisplayString
        MAX-ACCESS      read-write
        STATUS          current
        DESCRIPTION
            "Hostname used with HTTPS proxy client"
        ::= { proxyMgmt 10 }

   proxyMgmtHttpsPort OBJECT-TYPE
        SYNTAX          Integer32
        MAX-ACCESS      read-write
        STATUS          current
        DESCRIPTION
            "Port used with HTTPS proxy client"
        ::= { proxyMgmt 11 }

   proxyMgmtHttpsUsername OBJECT-TYPE
        SYNTAX          DisplayString
        MAX-ACCESS      read-write
        STATUS          current
        DESCRIPTION
            "Username used with HTTPS proxy client"
        ::= { proxyMgmt 12 }

   proxyMgmtHttpsPassword OBJECT-TYPE
        SYNTAX          DisplayString
        MAX-ACCESS      read-write
        STATUS          current
        DESCRIPTION
            "Password used with HTTPS proxy client"
        ::= { proxyMgmt 13 }

   proxyMgmtHttpsType OBJECT-TYPE
        SYNTAX          INTEGER { https(1) }
        MAX-ACCESS      read-write
        STATUS          current
        DESCRIPTION
            "HTTPS proxy client Type"
        ::= { proxyMgmt 14 }

   proxyMgmtSocksEnabled OBJECT-TYPE
        SYNTAX          INTEGER { disable(0), enable(1) }
        MAX-ACCESS      read-write
        STATUS          current
        DESCRIPTION
            "Disable or enable SOCKS proxy client"
        ::= { proxyMgmt 15 }

   proxyMgmtSocksIpAddr OBJECT-TYPE
        SYNTAX          IpAddress
        MAX-ACCESS      read-write
        STATUS          current
        DESCRIPTION
            "Ip Address used with SOCKS proxy client"
        ::= { proxyMgmt 16 }

   proxyMgmtSocksPort OBJECT-TYPE
        SYNTAX          Integer32
        MAX-ACCESS      read-write
        STATUS          current
        DESCRIPTION
            "Port used with SOCKS proxy client"
        ::= { proxyMgmt 17 }

   proxyMgmtSocksUsername OBJECT-TYPE
        SYNTAX          DisplayString
        MAX-ACCESS      read-write
        STATUS          current
        DESCRIPTION
            "Username used with SOCKS proxy client"
        ::= { proxyMgmt 18 }

   proxyMgmtSocksPassword OBJECT-TYPE
        SYNTAX          DisplayString
        MAX-ACCESS      read-write
        STATUS          current
        DESCRIPTION
            "Password used with SOCKS proxy client"
        ::= { proxyMgmt 19 }

   proxyMgmtSocksType OBJECT-TYPE
        SYNTAX          INTEGER { socks4(2), socks5(3) }
        MAX-ACCESS      read-write
        STATUS          current
        DESCRIPTION
            "SOCKS proxy client Type"
        ::= { proxyMgmt 20 }


   proxyMgmtSubnet01 OBJECT-TYPE
        SYNTAX          IpAddress
        MAX-ACCESS      read-write
        STATUS          current
        DESCRIPTION
            "Socks Proxy Client Whitelist Local Network 01"
        ::= { proxyMgmt 21 }

   proxyMgmtMask01 OBJECT-TYPE
        SYNTAX          IpAddress
        MAX-ACCESS      read-write
        STATUS          current
        DESCRIPTION
            "Socks Proxy Client Whitelist Local Network Mask 01"
        ::= { proxyMgmt 22 }

   proxyMgmtSubnet02 OBJECT-TYPE
        SYNTAX          IpAddress
        MAX-ACCESS      read-write
        STATUS          current
        DESCRIPTION
            "Socks Proxy Client Whitelist Local Network 02"
        ::= { proxyMgmt 23 }

   proxyMgmtMask02 OBJECT-TYPE
        SYNTAX          IpAddress
        MAX-ACCESS      read-write
        STATUS          current
        DESCRIPTION
            "Socks Proxy Client Whitelist Local Network Mask 02"
        ::= { proxyMgmt 24 }


   proxyMgmtSubnet03 OBJECT-TYPE
        SYNTAX          IpAddress
        MAX-ACCESS      read-write
        STATUS          current
        DESCRIPTION
            "Socks Proxy Client Whitelist Local Network 03"
        ::= { proxyMgmt 25 }

   proxyMgmtMask03 OBJECT-TYPE
        SYNTAX          IpAddress
        MAX-ACCESS      read-write
        STATUS          current
        DESCRIPTION
            "Socks Proxy Client Whitelist Local Network Mask 03"
        ::= { proxyMgmt 26 }

   proxyMgmtSubnet04 OBJECT-TYPE
        SYNTAX          IpAddress
        MAX-ACCESS      read-write
        STATUS          current
        DESCRIPTION
            "Socks Proxy Client Whitelist Local Network 04"
        ::= { proxyMgmt 27 }

   proxyMgmtMask04 OBJECT-TYPE
        SYNTAX          IpAddress
        MAX-ACCESS      read-write
        STATUS          current
        DESCRIPTION
            "Socks Proxy Client Whitelist Local Network Mask 04"
        ::= { proxyMgmt 28 }

   proxyMgmtSubnet05 OBJECT-TYPE
        SYNTAX          IpAddress
        MAX-ACCESS      read-write
        STATUS          current
        DESCRIPTION
            "Socks Proxy Client Whitelist Local Network 05"
        ::= { proxyMgmt 29 }

   proxyMgmtMask05 OBJECT-TYPE
        SYNTAX          IpAddress
        MAX-ACCESS      read-write
        STATUS          current
        DESCRIPTION
            "Socks Proxy Client Whitelist Local Network Mask 05"
        ::= { proxyMgmt 30 }

   proxyMgmtSubnet06 OBJECT-TYPE
        SYNTAX          IpAddress
        MAX-ACCESS      read-write
        STATUS          current
        DESCRIPTION
            "Socks Proxy Client Whitelist Local Network 06"
        ::= { proxyMgmt 31 }

   proxyMgmtMask06 OBJECT-TYPE
        SYNTAX          IpAddress
        MAX-ACCESS      read-write
        STATUS          current
        DESCRIPTION
            "Socks Proxy Client Whitelist Local Network Mask 06"
        ::= { proxyMgmt 32 }

   proxyMgmtSubnet07 OBJECT-TYPE
        SYNTAX          IpAddress
        MAX-ACCESS      read-write
        STATUS          current
        DESCRIPTION
            "Socks Proxy Client Whitelist Local Network 07"
        ::= { proxyMgmt 33 }

   proxyMgmtMask07 OBJECT-TYPE
        SYNTAX          IpAddress
        MAX-ACCESS      read-write
        STATUS          current
        DESCRIPTION
            "Socks Proxy Client Whitelist Local Network Mask 07"
        ::= { proxyMgmt 34 }

   proxyMgmtSubnet08 OBJECT-TYPE
        SYNTAX          IpAddress
        MAX-ACCESS      read-write
        STATUS          current
        DESCRIPTION
            "Socks Proxy Client Whitelist Local Network 08"
        ::= { proxyMgmt 35 }

   proxyMgmtMask08 OBJECT-TYPE
        SYNTAX          IpAddress
        MAX-ACCESS      read-write
        STATUS          current
        DESCRIPTION
            "Socks Proxy Client Whitelist Local Network Mask 08"
        ::= { proxyMgmt 36 }

   proxyMgmtSubnet09 OBJECT-TYPE
        SYNTAX          IpAddress
        MAX-ACCESS      read-write
        STATUS          current
        DESCRIPTION
            "Socks Proxy Client Whitelist Local Network 09"
        ::= { proxyMgmt 37 }

   proxyMgmtMask09 OBJECT-TYPE
        SYNTAX          IpAddress
        MAX-ACCESS      read-write
        STATUS          current
        DESCRIPTION
            "Socks Proxy Client Whitelist Local Network Mask 09"
        ::= { proxyMgmt 38 }

   proxyMgmtSubnet10 OBJECT-TYPE
        SYNTAX          IpAddress
        MAX-ACCESS      read-write
        STATUS          current
        DESCRIPTION
            "Socks Proxy Client Whitelist Local Network 10"
        ::= { proxyMgmt 39 }

   proxyMgmtMask10 OBJECT-TYPE
        SYNTAX          IpAddress
        MAX-ACCESS      read-write
        STATUS          current
        DESCRIPTION
            "Socks Proxy Client Whitelist Local Network Mask 10"
        ::= { proxyMgmt 40 }


END
